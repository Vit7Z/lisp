;/////// *************************************************************///////////////////////////////////////////////////////////////////////////////////////////////////////////
;/////// круг 10 мм                                                   ///////////////////////////////////////////////////////////////////////////////////////////////////////////
;/////// *************************************************************///////////////////////////////////////////////////////////////////////////////////////////////////////////
(defun c:10-circle-r-10 

( / adoc pnt-ins)

(vl-load-com)
(vla-startundomark (setq adoc (vla-get-activedocument (vlax-get-acad-object))));start undo

(setvar "cmdecho" 0)
(setvar "osmode" 6199)

(if (= (tblsearch "layer" "wspom") nil)
	(command "_layer" "Создать" "wspom" "Тип" "Continuous" "wspom" "Цвет" 3 "wspom" "Установить" "wspom" ""); создаем слой
	(command "_layer" "Установить" "wspom" "") ; устанавливаем слой
); end if

(while (/= (setq pnt-ins (getpoint "\nУкажите точку вставки\n")) nil)
	
	(setvar "osmode" 0)	
	
	(command "_circle" pnt-ins 5) ; чертим прямоугольник

	(setvar "osmode" 6199)
	
);while

(command "_layer" "Установить" "0" "") ; устанавливаем слой предыдущий слой		

(setvar "osmode" 6199)
(setvar "cmdecho" 1)

(vla-endundomark adoc)
(princ)
)
;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////
