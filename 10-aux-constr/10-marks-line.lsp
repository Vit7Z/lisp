;/////// *************************************************************////////////////////
;/////// название программы****************                           ////////////////////
;/////// *************************************************************////////////////////
(defun c:10-marks-line

( / adoc pnt1 pnt2)

(vl-load-com)
(vla-startundomark (setq adoc (vla-get-activedocument (vlax-get-acad-object))));start undo

(setvar "cmdecho" 0)
(setvar "osmode" 0)

(if (= (tblsearch "layer" "wspom") nil)
	(entmakex 
		'((0 . "LAYER")
  	(100 . "AcDbSymbolTableRecord")
  	(100 . "AcDbLayerTableRecord")
  	(2 . "wspom")
  	(70 . 0) ;standard flags (bit-coded values): 1 = Layer is frozen
  	(62 . 3) ;color
  	(6 . "Continuous") ;linetype name
  	(290 . 1) ;plotting flag. If set to 0, do not plot this layer
  	(370 . -1)) ;lineweight enum value; line wide 0
	);entmakex
);if


(setq pnt1 (getpoint "Точка 1")
			pnt2 (getpoint "Точка 2")
);setq


(entmakex
	(list
		'(0 . "LINE")
		'(100 . "AcDbLine")
		'(100 . "AcDbEntity")
		(cons 10 pnt1)
		(cons 11 pnt2)
		'(370 . 60)
		'(62 . 1)
		'(8 . "wspom")
	);list
);entmakex

(setvar "osmode" 6199)
(setvar "cmdecho" 1)

(vla-endundomark adoc)
(princ)
(gc)
)

;/////// *************************************************************////////////////////
;/////// КОНЕЦ ПРОГРАММЫ                                              ////////////////////
;/////// *************************************************************////////////////////
