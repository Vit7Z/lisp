;/////// *************************************************************///////////////////////////////////////////////////////////////////////////////////////////////////////////
;/////// рисование квадрата со стороной 25мм на слое wspom            ///////////////////////////////////////////////////////////////////////////////////////////////////////////
;/////// *************************************************************///////////////////////////////////////////////////////////////////////////////////////////////////////////
(defun c:10-square-12

( / adoc p1)

(vl-load-com)
(vla-startundomark (setq adoc (vla-get-activedocument (vlax-get-acad-object))));start undo

(if (= (tblsearch "layer" "wspom") nil)
	(command "_layer" "Создать" "wspom" "Тип" "Continuous" "wspom" "Цвет" 3 "wspom" "Установить" "wspom" "");слой
);if

(setvar "cmdecho" 0)
(setvar "osmode" 6199)
(setvar	"clayer" "wspom")

(setq p1 (getpoint "\nУкажите точку вставки\n"));setq

(setvar "osmode" 0)

(command "_rectangle" p1 "Размеры" 12 12 pause) ; чертим прямоугольник

(setvar	"clayer" "0")
(setvar "osmode" 6199)
(setvar "cmdecho" 1)

(vla-endundomark adoc)
(princ)
)
;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////
