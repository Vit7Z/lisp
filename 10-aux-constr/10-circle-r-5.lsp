;/////// *************************************************************///////////////////////////////////////////////////////////////////////////////////////////////////////////
;/////// круг 5 мм                                                    ///////////////////////////////////////////////////////////////////////////////////////////////////////////
;/////// *************************************************************///////////////////////////////////////////////////////////////////////////////////////////////////////////
(defun c:10-circle-r-5 

( / adoc circle-1 pnt-ins)

(vl-load-com)

(vla-startundomark (setq adoc (vla-get-activedocument (vlax-get-acad-object))));start undo

(setvar "cmdecho" 0)
(setvar "osmode" 6199)

(if (= (tblsearch "layer" "wspom") nil)
	(command "_layer" "Создать" "wspom" "Тип" "Continuous" "wspom" "Цвет" 3 "wspom" "Установить" "wspom" "");создаем слой
);if

(while (/= (setq pnt-ins (getpoint "\nУкажите точку вставки\n")) nil)
	
	(setvar "osmode" 0)	
	
	(setq circle-1
		(entmakex
			(list
				'(0 . "CIRCLE")
				'(100 . "AcDbCircle")
				(cons 10 pnt-ins)
				'(40 . 2.5)
				'(8 . "wspom")
;				'(6 . "acad_iso02w100")
			);list
		);entmakex
	);setq
	
	(setvar "osmode" 6199)
	
);while

(command "_layer" "Установить" "0" "") ; устанавливаем слой предыдущий слой		

(setvar "osmode" 6199)
(setvar "cmdecho" 1)

(vla-endundomark adoc)
(princ)
)
;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////
