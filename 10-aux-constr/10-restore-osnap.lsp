;/////// ************************************************************ //////////
;/////// восстановление привязок                                     ///////////
;/////// ************************************************************ //////////
(defun c:10-restore-osnap

()

(setvar "cmdecho" 0)

(setvar "osmode" 6199)
(setvar "autosnap" 63)
(setvar "celweight" -1)
(setvar "cecolor" "ByLayer")
(setvar "celtscale" 1)
(setvar "celtype" "ByLayer")

(command "_layer" "Установить" "0" "")

(setvar "cmdecho" 1)
(princ)
)
;/////// ************************************************************ //////////
;/////// конец                                                       ///////////
;/////// ************************************************************ //////////
