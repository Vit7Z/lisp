;/////// ************************************************************ ///////////////////////////////////////////////////////////////////////////////////////////////////////////
;///////                                                              ///////////////////////////////////////////////////////////////////////////////////////////////////////////
;/////// ************************************************************ ///////////////////////////////////////////////////////////////////////////////////////////////////////////
(defun 101-08-clmp-klemsan-01-general-le

(list-902 / cntr-1 pnt-ins str-01 str-02 str-03 str-04 str-05 str-06 str-07 str-08 str-701 str-702 str-tmp)

(setq cntr-1 0);setq

(repeat (length list-902)
	(setq str-tmp (nth cntr-1 list-902)
				str-01 (cdr (assoc 1 str-tmp))
				str-02 (cdr (assoc 2 str-tmp))
				str-03 (cdr (assoc 3 str-tmp))
	);setq

;(princ "\n         str-tmp = ") (princ str-tmp);Erase_DV
;(getstring "\nPress Enter to continue...");Erase_DV
	
	(setvar "osmode" 6199)
	
	(setq pnt-ins (getpoint "\nУкажите точку вставки\n"));setq

	;;;;;;;///////////////////////////////////////////////////////////////////////////////////////////
	(if (or (= str-01 "Клемма проходная")
          (= str-01 "Клемма с предохранителем")
          (= str-01 "Клемма заземления"));
       		
		(setq str-04 (cdr (assoc 4 str-tmp))
				  str-05 (cdr (assoc 5 str-tmp))
				  str-06 (cdr (assoc 6 str-tmp))
				  str-07 (cdr (assoc 7 str-tmp))

				  str-701 (strcat str-01 " Klemsan " str-02 ", " str-03 ", " str-04 ", " str-05 ", " str-06 ", " str-07)
				  str-702 nil			
		);setq
	);if
	
	;;;;;;;///////////////////////////////////////////////////////////////////////////////////////////
	(if (= "Перемычка" str-01)
		(setq str-04 (cdr (assoc 4 str-tmp))
					str-05 (cdr (assoc 5 str-tmp))
						
					str-701 (strcat str-01 " Klemsan " str-02 ", " str-03 ", " str-04 ", " str-05)
					str-702 nil								
		);setq
	);if
	
	
	;;;;;;;///////////////////////////////////////////////////////////////////////////////////////////
	(if (= "Стопор концевой" str-01)
		(setq str-04 (cdr (assoc 4 str-tmp))
					str-04 (strcase str-04 1)			
						
					str-701 (strcat str-01 " Klemsan " str-02 ", " str-03 ", " str-04)
					str-702 nil
		);setq
	);if
	
	;;;;;;;///////////////////////////////////////////////////////////////////////////////////////////	
	(if (= "Держатель Маркировки клем. групп" str-01)
		(setq 
		
		
		
		str-tmp-1 (strcat str-tmp-0 " Phoenix Contact " str-tmp-1 ",")
					str-tmp-2 (strcat "артикул " str-tmp-2 ", цвет " (strcase str-tmp-3 1) ", " (strcase str-tmp-4 1))
		);setq
	);if
	
	
	
	
	


;	;;;;;;;///////////////////////////////////////////////////////////////////////////////////////////
;	(if (= "Крышка концевая" str-tmp-0)
;		(progn
;					
;			(cond
;				((= "Для 1 ур. клемм" str-tmp-4) (setq str-tmp-4 "для одноуровневых клемм"));=
;				((= "Для 2-х ур. клемм" str-tmp-4) (setq str-tmp-4 "для двухуровневых клемм"));=
;				((= "Для силовых клемм" str-tmp-4) (setq str-tmp-4 "для силовых клемм"));=
;			);cond
;					
;			(setq nmbr-ln 3
;						str-tmp-1 (strcat str-tmp-0 " Phoenix Contact " str-tmp-1 ",")
;						str-tmp-2 (strcat "артикул " str-tmp-2 ", цвет " str-tmp-3 ", " str-tmp-4)
;			);setq
;		);progn
;	);if



	(split-str-parts-le-01-general str-701 str-702 pnt-ins "**1**");

	(setq cntr-1 (+ cntr-1 1));setq
);repeat

(princ)
)
;;;;/////////////////////////////////////////////////////////////////////////////////////////////////////////////////////////////////////////////////////////////////////////////
;;;;/////////////////////////////////////////////////////////////////////////////////////////////////////////////////////////////////////////////////////////////////////////////
