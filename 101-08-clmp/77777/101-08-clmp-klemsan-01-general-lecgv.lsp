;/////// ************************************************************ ///////////////////////////////////////////////////////////////////////////////////////////////////////////
;///////                                                              ///////////////////////////////////////////////////////////////////////////////////////////////////////////
;/////// ************************************************************ ///////////////////////////////////////////////////////////////////////////////////////////////////////////
(defun 101-08-clmp-klemsan-01-general-lecgv

(list-902 / cntr-1 pnt-ins str-00 str-01 str-02 str-03 str-04 str-05 str-06 str-07 str-08 str-701 str-702 str-703 str-99 str-tmp)

(setq cntr-1 0);setq

(repeat (length list-902)
	(setq str-tmp (nth cntr-1 list-902)				
				str-01 (cdr (assoc 1 str-tmp))
				str-02 (cdr (assoc 2 str-tmp))
				str-03 (cdr (assoc 3 str-tmp))
				str-04 (cdr (assoc 4 str-tmp))
				
				str-99 (cdr (assoc 99 str-tmp))
	);setq
	
	(setvar "osmode" 6199)
	
	(setq pnt-ins (getpoint "\nУкажите точку вставки\n"));setq

	;;;;;;;///////////////////////////////////////////////////////////////////////////////////////////
	(if (or (= str-01 "Клемма Проходная Винт")
          (= str-01 "Клемма Проходная Пружин")
          (= str-01 "Клемма Проходная Push-In")
			 		(= str-01 "Клемма Защитного провода")
       		(= str-01 "Клемма Электротехническая"));
       		
		(setq str-01 (strcase str-01 1)
					str-01 (vl-string-subst "Клемма" "клемма" str-01)
					str-05 (cdr (assoc 5 str-tmp))
					str-06 (strcase (vl-string-subst "ч" "Ч" (cdr (assoc 6 str-tmp))) 1)						
					str-07 (strcase (cdr (assoc 7 str-tmp)) 1)
					
					str-701 (strcat str-01 " Klemsan " str-02 ", артикул " str-03 ", сечение проводника " str-05 "мм2, цвет " str-06 ", " str-07)		
					str-702 nil
					str-703 nil
		);setq
	);if
	
	
	;;;;;;;///////////////////////////////////////////////////////////////////////////////////////////
	(if (= str-01 "Клемма С Предохранителем")      		
		(setq str-01 (strcase str-01 1)
					str-01 (vl-string-subst "Клемма" "клемма" str-01)
					str-05 (cdr (assoc 5 str-tmp))
					str-06 (strcase (vl-string-subst "ч" "Ч" (cdr (assoc 6 str-tmp))) 1)
					str-07 (cdr (assoc 7 str-tmp))						
					str-08 (strcase (cdr (assoc 8 str-tmp)) 1)
					
					str-701 (strcat str-01 " Klemsan " str-02 ", артикул " str-03 ", сечение проводника " str-05 "мм2, " str-07 ", " str-08 " зажим")		
					str-702 nil
					str-703 nil
		);setq
	);if
		
	;;;;;;;///////////////////////////////////////////////////////////////////////////////////////////
	(if (= "Перемычка" str-01)
		(setq str-04 (cdr (assoc 4 str-tmp))
					str-05 (cdr (assoc 5 str-tmp))
						
					str-701 (strcat str-01 " Klemsan " str-02 ", артикул " str-03 ", кол. контактов " str-04 ", для клемм шириной " str-05 "мм")
					str-702 nil		
					str-703 nil											
		);setq
	);if
	
	;;;;;;;///////////////////////////////////////////////////////////////////////////////////////////
	(if (= "Стопор Концевой" str-01)
		(setq str-04 (strcase str-04 1)			
						
					str-701 (strcat str-01 " Klemsan " str-02 ", артикул " str-03 ", " str-04)
					str-702 nil
					str-703 nil
		);setq
	);if
	
	

	;!!!!!!!!!!!!!!!!!!!!!!!!!!!!!!!!!!!!!!!!!!!

	(split-str-parts-lecgv-01-general str-701 str-702 str-703 str-99 pnt-ins);

	(setq cntr-1 (+ cntr-1 1));setq
);repeat

(princ)
)
;;;;/////////////////////////////////////////////////////////////////////////////////////////////////////////////////////////////////////////////////////////////////////////////
;;;;/////////////////////////////////////////////////////////////////////////////////////////////////////////////////////////////////////////////////////////////////////////////
