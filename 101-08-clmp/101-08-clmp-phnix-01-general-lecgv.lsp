;/////// ************************************************************ ///////////////////////////////////////////////////////////////////////////////////////////////////////////
;///////                                                              ///////////////////////////////////////////////////////////////////////////////////////////////////////////
;/////// ************************************************************ ///////////////////////////////////////////////////////////////////////////////////////////////////////////
(defun 101-08-clmp-phnix-01-general-lecgv

(list-902 / cntr-1 pnt-ins str-00 str-01 str-02 str-03 str-04 str-05 str-06 str-07 str-701 str-702 str-703 str-99 str-tmp str-txt str-txt-01 str-txt-02)

(setq cntr-1 0);setq

(repeat (length list-902)
	(setq str-tmp (nth cntr-1 list-902)				
			str-01 (cdr (assoc 1 str-tmp))
			str-02 (cdr (assoc 2 str-tmp))
			str-03 (cdr (assoc 3 str-tmp))
			str-04 (cdr (assoc 4 str-tmp))
			str-05 (cdr (assoc 5 str-tmp))
			str-99 (cdr (assoc 99 str-tmp))
	);setq
	
	(setvar "osmode" 6199)
	
	(setq pnt-ins (getpoint "\nУкажите точку вставки\n"));setq

	;;;;;;;///////////////////////////////////////////////////////////////////////////////////////////
	(if (or (= str-01 "Клемма Проходная")
			 		(= str-01 "Клемма Защитного провода")
       		(= str-01 "Клемма С предохранителем")
       		(= str-01 "Клемма Электротехническая"));
       		
		(setq str-01 (strcase str-01 1)
					str-01 (vl-string-subst "Клемма" "клемма" str-01)
					str-06 (strcase (vl-string-subst "ч" "Ч" (cdr (assoc 6 str-tmp))) 1)						
					str-07 (strcase (cdr (assoc 7 str-tmp)) 1)
					
					str-701 (strcat str-01 " Phoenix Contact " str-02 ",  артикул " str-03 ", сечение проводника " str-05 "мм2, цвет " str-06 ", " str-07 " зажим")		
					str-702 nil
					str-703 nil
		);setq
	);if
	
	;!!!!!!!!!!!!!!!!!!!!!!!!!!!!!!!!!!!!!!!!!!!
	

	;/////////////////////////////////////////////////////////////////////////////////////////////////////////////////////
	(if (= "Наконечник кабельный" str-00)
		(setq str-04 (strcase (vl-string-subst "ч" "Ч" str-04) 1)
					str-05 (cdr (assoc 5 str-tmp))
						
					str-701 (strcat "Наконечник кабельный Phoenix Contact, артикул " str-02 ", сечение проводника " str-03 "мм2, цвет " str-04 ", длина гильзы " str-05 "мм")		
					str-702 nil
					str-703 nil									
		);setq
	);if


	;/////////////////////////////////////////////////////////////////////////////////////////////////////////////////////
	(if (= "Стопор концевой" str-01)
		(progn
			(setq str-05 (cdr (assoc 5 str-tmp)));setq

			(cond
				((wcmatch str-05 "*винт*") (setq str-05 "винтами"));=
				((wcmatch str-05 "*щелка*") (setq str-05 "защелкой"));=
			);cond
			
			(setq str-701 (strcat "Стопор концевой Phoenix Contact " str-02 ", артикул " str-03 ", крепление " str-05)		
						str-702 nil
						str-703 nil					
			);setq
						
			(cond
				((wcmatch str-02 "*CLIPFIX*") (setq str-701 (strcat str-701 ", для проходных клемм")));=
				((wcmatch str-02 "*E/AL*") (setq str-701 (strcat str-701 ", для сильноточных клемм")));=
			);cond
		);progn
	);if	

	;;;;;;;///////////////////////////////////////////////////////////////////////////////////////////
	(if (= "Планка Zack (маркировка клемм)" str-01)
		(progn
			(setq str-702 nil
					str-703 nil														
			);setq

			(if (wcmatch str-02 "ZB #:UNBEDRUCKT")
				(setq str-701 (strcat "Планка (маркировка клемм) Phoenix Contact " str-02 ", артикул " str-03 ", " str-05));setq
			);if

			(if (wcmatch str-02 "ZB # QR:FORTL.ZAHLEN")
				(setq str-05 (cdr (assoc 5 str-tmp))
						str-07 (cdr (assoc 7 str-tmp))
						str-701 (strcat "Планка (маркировка клемм) Phoenix Contact " str-02 ", артикул " str-03 ", цифры " str-07 ", расположение символов " str-05)						
				);setq
			);if
		);progn
	);if


	;/////////////////////////////////////////////////////////////////////////////////////////////////////////////////////
	(if (= "Держатель маркировочных полос" str-01)
		(setq str-701 (strcat "Держатель маркировочных полос Phoenix Contact " str-02 ", артикул " str-03 ", маркировочное поле " str-04 "мм, для CLIPFIX 35 (E/UK, E/NS 35 N)")						
					str-702 nil
					str-703 nil
		);setq
	);if


	;/////////////////////////////////////////////////////////////////////////////////////////////////////////////////////
	(if (= "Соединитель поперечный" str-01)
		(setq str-txt-01 nil
					str-txt-02 nil
					str-txt (strcat "Соединитель поперечный Phoenix Contact, артикул " str-02 ", кол. полюсов " str-04)						
		);setq
	);if

	;/////////////////////////////////////////////////////////////////////////////////////////////////////////////////////
	(if (= "Полоса маркировочная" str-01)
		(setq str-04 (strcase str-04 1)	
					str-06 (cdr (assoc 6 str-tmp))
					
					str-701 (strcat "Полоса маркировочная Phoenix Contact " str-02 ", артикул " str-03 ", цвет " str-04 ", маркировочное поле " str-06 "мм")
					str-702 nil
					str-703 nil						
		);setq
	);if

	;/////////////////////////////////////////////////////////////////////////////////////////////////////////////////////
	(if (= "Пластина разделительная" str-01)
		(setq str-701 (strcat "Пластина разделительная Phoenix Contact, артикул " str-02)
					str-702 nil
					str-703 nil						
		);setq
	);if

	(split-str-parts-lecgv-01-general str-701 str-702 str-703 str-99 pnt-ins);

	(setq cntr-1 (+ cntr-1 1));setq
);repeat

(princ)
)
;;;;/////////////////////////////////////////////////////////////////////////////////////////////////////////////////////////////////////////////////////////////////////////////
;;;;/////////////////////////////////////////////////////////////////////////////////////////////////////////////////////////////////////////////////////////////////////////////
