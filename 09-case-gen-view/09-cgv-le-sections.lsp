;/////// ************************************************************ /////////////////////////////////////////////////////////////////////////////////////////////////////////////////////////////////////////
;/////// заголовки спецификации ОВШ                                   /////////////////////////////////////////////////////////////////////////////////////////////////////////////////////////////////////////
;/////// ************************************************************ /////////////////////////////////////////////////////////////////////////////////////////////////////////////////////////////////////////
(defun c:09-cgv-le-sections

( / adoc dcl-id list-01 list-01-read-file list-02 list-02-read-file str-01)

(vl-load-com)
(vla-startundomark (setq adoc (vla-get-activedocument (vlax-get-acad-object))));start undo

(09-cgv-le-empty-line-02)

(read-file-for-dialog-box-01 "09-cgv-le-sections.txt" 2);setq

(setq str-01 "0"		
			list-01 list-01-read-file
);setq

(txt-01-09-cgv-le-sections str-01 list-02-read-file)

(if (< (setq dcl-id (load_dialog "dia-09-cgv-le-sections.dcl")) 0) ;ищем диалог
	(progn
		(alert "Не найден dcl-файл")
		(exit)
	);progn
);if

(if (not (new_dialog "dia_09_cgv_le" dcl-id))
		(exit)
);if

(list-filling "txt-01" list-01)
(list-filling "txt-02" list-02)

(set_tile "txt-01" "0")

(action_tile "txt-01"
  (strcat "(setq str-01 (get_tile \"txt-01\"))"
					"(txt-01-09-cgv-le-sections str-01 list-02-read-file)"
  );strcat
);action_tile

(action_tile "accept"
  (strcat "(setq str-01 (get_tile \"txt-01\"))"
  				"(done_dialog)"
  );strcat
);action_tile

(start_dialog)
(unload_dialog dcl-id)

(01-09-cgv-le-sections str-01 list-01-read-file)

(vla-endundomark adoc)	

(setvar "osmode" 6199)
(setvar "cmdecho" 1)
(setvar "orthomode" 1)

(princ)
)
;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////


;;;;/////////////////////////////////////////////////////////////////////////////////////////////////////////////////////////////////////////////////////////////////////////////
;;;;/////////////////////////////////////////////////////////////////////////////////////////////////////////////////////////////////////////////////////////////////////////////
(defun txt-01-09-cgv-le-sections

(str-01 list-02-read-file / list-900-read-file)

(setq list-02 (nth (atoi str-01) list-02-read-file));setq

(divide-text-into-parts list-02 53)

(setq list-02 list-900-read-file);setq

(list-filling "txt-02" list-02)

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun 01-09-cgv-le-sections

(str-01 list-01 / nmbr-ln pnt-ins right-bottom st-1 txt-01 txt-1 x-pnt-ins y-pnt-ins y-pnt-ins-1)

(setvar "OSMODE" 6199)
(setvar "cmdecho" 0)

(setq txt-01 (nth (atoi str-01) list-01)
			txt-01 (strcat "%%u" txt-01)

			pnt-ins (getpoint "\nУкажите точку вставки\n")
			x-pnt-ins (nth 0 pnt-ins)
			y-pnt-ins (nth 1 pnt-ins)
			y-pnt-ins-1 y-pnt-ins
			nmbr-ln 3
);setq

(setq right-bottom (+ (* nmbr-ln 8) 2));setq

(setvar "OSMODE" 0)

(setq st-1 (ssget "_c" (list (+ x-pnt-ins 169) (- y-pnt-ins 1)) (list (- x-pnt-ins 14) (- y-pnt-ins 23))));setq

(if (/= st-1 nil) (command "_erase" st-1 ""));if

(setq txt-1 
	(entmakex
  	(list
    	'(0 . "TEXT")
      '(100 . "AcDbEntity")
      '(100 . "AcDbText")
      (cons 10 (list (+ x-pnt-ins 92.5) (- y-pnt-ins 12))) ; нач точка текста
      (cons 11 (list (+ x-pnt-ins 92.5) (- y-pnt-ins 12))) ; нач точка текста
      (cons 1 txt-01) ; содержание текста
      '(40 . 3.5) ; высота текста
      '(41 . 1) ; растяжение текста
      '(50 . 0) ; поворот текста
      '(72 . 1) ; гориз выравнивание текста
      '(73 . 2) ; верт выравнивание текста
      '(370 . -1) ; толщина текста
      (cons 7 (getvar "textstyle")) ; стиль текста
		);list
	);entmakex
);setq

(repeat nmbr-ln
  (command "_insert" "овш-пэ-пустая-строка" "_X" 1 "_Y" 1 "_Z" 1 "_R" 0 (list x-pnt-ins y-pnt-ins-1))
  (setq y-pnt-ins-1 (- y-pnt-ins-1 8));setq
);repeat

(princ)
)
;;;;/////////////////////////////////////////////////////////////////////////////////////////////////////////////////////////////////////////////////////////////////////////////
;;;;/////////////////////////////////////////////////////////////////////////////////////////////////////////////////////////////////////////////////////////////////////////////
