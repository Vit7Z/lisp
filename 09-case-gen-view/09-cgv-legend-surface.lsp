;/////// ************************************************************ ///////////////////////////////////////////////////////////////////////////////////////////////////////////
;/////// рисование кабель-каналов на ОВШ                             ////////////////////////////////////////////////////////////////////////////////////////////////////////////
;/////// ************************************************************ ///////////////////////////////////////////////////////////////////////////////////////////////////////////
(defun 09-cgv-legend-surface

( / adoc dcl-id list-01 list-01-read-file pnt-1 str-01 txt-01)

(setvar "osmode" 0)
(setvar "cmdecho" 0)

(vl-load-com)
(vla-startundomark (setq adoc (vla-get-activedocument (vlax-get-acad-object))));start undo

(read-file-for-dialog-box-01 "09-cgv-legend-surface.txt" 1)

(setq list-01 list-01-read-file);setq

(if (< (setq dcl-id (load_dialog "dia-09-cgv-legend-surface.dcl")) 0) ;ищем диалог
		(progn
			(alert "Не найден dcl-файл")
			(exit)
		);progn
);if

(if (not (new_dialog "dia_09_legend_surface" dcl-id))
		(exit)
);if

(list-filling "txt-01" list-01)

(set_tile "txt-01" "0")

(action_tile "txt-01"
  (strcat "(setq str-01 (get_tile \"txt-01\"))"
  				"(setq str-01 (nth (atoi str-01) list-01))"
  				"(done_dialog)"
  );strcat
);action_tile

(action_tile "accept"
  (strcat "(done_dialog)"
          "(exit)"
  );strcat
);action_tile

(start_dialog)
(unload_dialog dcl-id)


(cond 
	((or (wcmatch str-01 "Вид на переднюю*") 
			 (wcmatch str-01 "Вид на внутренние*"))
	(09-cgv-legend-surface-01 str-01));=

	((or (wcmatch str-01 "Левая стенка") 
			 (wcmatch str-01 "Правая стенка"))
	(09-cgv-legend-surface-02 str-01));=

);cond

(vla-endundomark adoc)
(setvar "osmode" 6199)
(setvar "cmdecho" 1)
(princ)
)
;///////////////////////////////////// конец программы //////////////////////////////////////////////////////////////////////////////////////////////////////////////////////////

;;;;;/////////////////////////////////////////////////////////////////////////////////////////////////////////////////////////////////////////////////////////////////////////////
;;;;;рисуем по сстороне                         //////////////////////////////////////////////////////////////////////////////////////////////////////////////////////////////////
(defun 09-cgv-legend-surface-01 

(str-01 / pnt-1 txt-01)

(setvar "osmode" 6199)

(setq pnt-1 (getpoint "\nУкажите точку вставки\n"));setq

(setvar "osmode" 0)

(cond 
	((wcmatch str-01 "Вид на переднюю*") (setq str-01 "\\LВид на переднюю панель \\P\\l1:10"));=
	((wcmatch str-01 "Вид на внутренние*") (setq str-01 "\\LВид на внутренние поверхности (развернуто) \\P\\l1:10"));=
);if


(setq txt-01
  (entmakex
    (list
      '(0 . "MTEXT")
      '(100 . "AcDbEntity")
      '(100 . "AcDbMText")
      (cons 10 pnt-1) 
      (cons 1 str-01) 
      '(8 . "0")
      '(40 . 2.5) 
      '(41 . 76) 
      '(42 . 76) 
      '(71 . 5) 
      '(370 . -1) 
       (cons 7 (getvar "textstyle")) 
    );list
  );entmakex
);setq

(princ)
)
;;;;;////////////////////////////////////////////////////////////////////////////////////////////////////////////////////////////////////////////////////////////////////////////
;;;;;////////////////////////////////////////////////////////////////////////////////////////////////////////////////////////////////////////////////////////////////////////////


;;;;;/////////////////////////////////////////////////////////////////////////////////////////////////////////////////////////////////////////////////////////////////////////////
;;;;;рисуем по сстороне                         //////////////////////////////////////////////////////////////////////////////////////////////////////////////////////////////////
(defun 09-cgv-legend-surface-02 

(str-01 / )

(command "_qleader" pause pause "" 0 str-01 "")

(princ)
)
;;;;;////////////////////////////////////////////////////////////////////////////////////////////////////////////////////////////////////////////////////////////////////////////
;;;;;////////////////////////////////////////////////////////////////////////////////////////////////////////////////////////////////////////////////////////////////////////////
