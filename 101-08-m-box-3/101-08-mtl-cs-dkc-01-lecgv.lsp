;/////// ************************************************************ ///////////////////////////////////////////////////////////////////////////////////////////////////////////
;/////// подпрограмма вывода в овш                                    ///////////////////////////////////////////////////////////////////////////////////////////////////////////
;/////// ************************************************************ ///////////////////////////////////////////////////////////////////////////////////////////////////////////
(defun 101-08-mtl-cs-dkc-01-lecgv

(list-902 / cntr-1 pnt-ins str-01 str-02 str-03 str-04 str-701 str-702 str-703 str-97 str-98 str-99 str-tmp)

(setq cntr-1 0);setq

(repeat (length list-902)
	(setq str-tmp (nth cntr-1 list-902)
				str-01 (cdr (assoc 1 str-tmp))
				str-02 (cdr (assoc 2 str-tmp))
				
				str-97 (cdr (assoc 97 str-tmp))
				
				str-98 (cdr (assoc 98 str-tmp))
				str-99 (cdr (assoc 99 str-tmp))
				
				str-702 nil
				str-703 nil
	);setq
	
	(if (and (/= str-98 "шт.") (/= str-98 "шт"))
		(setq str-703 (strcat "Кол. в " str-98));setq
	);if
	
	
;(princ "\n         str-tmp = ") (princ str-tmp);Erase_DV
;(princ "\n         str-702 = ") (princ str-702);Erase_DV
;(getstring "\nPress Enter to continue...");Erase_DV
	
	(setvar "osmode" 6199)
	
	(setq pnt-ins (getpoint "\nУкажите точку вставки\n"));setq
	
	;/////////////////////////////////////////////////////////////////////////////
	(if (= "Шкаф сборный CQE" str-01)
		
		(setq str-701 (strcat str-01 ", " str-97 ", " str-02 ", в комплекте с дверью и задней панелью" ));setq
	);if
	
	;/////////////////////////////////////////////////////////////////////////////
	(if (= "Шкаф навесной ST" str-01)
	
		(setq str-701 (strcat str-01 ", " str-97 ", " str-02 ", в комплекте с дверью и монтажной панелью" ));setq
	);if

	;/////////////////////////////////////////////////////////////////////////////
	(if (or (= "Панели боковые" str-01)					
					(= "Панель монтажная" str-01)
					(= "Полка фиксированная" str-01)
					(= "DIN-рейка" str-01));or
					
		(setq str-03 (cdr (assoc 3 str-tmp))
			
					str-701 (strcat str-01 ", " str-97 ", " str-02  ", " str-03)
		);setq
	);if


	;/////////////////////////////////////////////////////////////////////////////
	(if (or (= "Цоколь (панели)" str-01)
					(= "Цоколь (элементы угловые)" str-01)
					(= "Карман для документации" str-01)
					(= "Ручка стандартная" str-01)
					(= "Зажим для кабеля" str-01)
					(= "Шина заземления" str-01)
					(= "Кабельный ввод" str-01)
					(= "Заглушка (дно шкафа)" str-01)
					(= "Короб перфорированный" str-01));or
		
		(setq str-701 (strcat str-01 ", " str-97 ", " str-02));setq
	);if
	
	
	;/////////////////////////////////////////////////////////////////////////////
	(if (= "DIN-рейка (С-профиль)" str-01)
		
		(setq str-03 (cdr (assoc 3 str-tmp))				
					str-04 (cdr (assoc 4 str-tmp))
					str-701 (strcat str-01 " " str-04 ", " str-97 ", " str-02 ", " str-03)
		);setq
	);if

	;/////////////////////////////////////////////////////////////////////////////
	(if (= "Кронштейн (для DIN-рейки)" str-01)
		
		(setq str-701 (strcat str-01 " " str-02 ", " str-97));setq
	);if

	;/////////////////////////////////////////////////////////////////////////////
	(if (= "Кронштейн (для 19\" профилей)" str-01)
		
		(setq str-701 (strcat str-01 ", " str-97));setq
	);if
	
	;/////////////////////////////////////////////////////////////////////////////
	(if (= "Панель для кабельных вводов" str-01)
			
		(setq str-03 (cdr (assoc 3 str-tmp))
					str-701 (strcat str-01 ", " str-97 ", " str-02 ", " str-03)
		);setq
	);if

	
	(split-str-parts-lecgv-01-general str-701 str-702 str-703 str-99 pnt-ins);
	
	(setq cntr-1 (+ cntr-1 1));setq
);repeat

(princ)
)
;;;;///////////////////////////////////////////////////////////////////////////////////////////////////////////////
;;;;///////////////////////////////////////////////////////////////////////////////////////////////////////////////
