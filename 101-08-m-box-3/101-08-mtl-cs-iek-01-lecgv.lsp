;/////// ************************************************************ //////////////////////////////////////////////////////////////////////
;/////// подпрограмма вывода в овш                                    //////////////////////////////////////////////////////////////////////
;/////// ************************************************************ //////////////////////////////////////////////////////////////////////
(defun 101-08-mtl-cs-iek-01-lecgv

(list-902 / cntr-1 pnt-ins str-01 str-02 str-03 str-04 str-701 str-702 str-703 str-97 str-98 str-99 str-tmp)

(setq cntr-1 0);setq

(repeat (length list-902)
	(setq str-tmp (nth cntr-1 list-902)
				str-01 (cdr (assoc 1 str-tmp))
				str-02 (cdr (assoc 2 str-tmp))
				
				str-98 (cdr (assoc 98 str-tmp))
				str-99 (cdr (assoc 99 str-tmp))
				
				str-702 nil
				str-703 nil
	);setq
	
	(if (and (/= str-98 "шт.") (/= str-98 "шт"))
		(setq str-703 (strcat "Кол. в " str-98));setq
	);if

	(setvar "osmode" 6199)
	
	(setq pnt-ins (getpoint "\nУкажите точку вставки\n"));setq
	
	;/////////////////////////////////////////////////////////////////////////////
	(if (or (= "Корпус металлический ЩМП" str-01)
					(= "Корпус металлический TITAN 5" str-01))
		
		(setq str-03 (cdr (assoc 3 str-tmp))				
					str-04 (cdr (assoc 4 str-tmp))
					
					str-701 (strcat "Корпус металлический IEK " str-02 ", " str-03 ", " str-04)
		);setq
	);if


	;/////////////////////////////////////////////////////////////////////////////
	(if (= "Кабель-канал перфорированный" str-01)
					
		(setq str-03 (cdr (assoc 3 str-tmp))
			
					str-701 (strcat str-01 " IEK, " str-02  ", " str-03)
		);setq
	);if

	
	;/////////////////////////////////////////////////////////////////////////////
	(if (= "DIN-рейка" str-01)
		
		(setq str-03 (cdr (assoc 3 str-tmp))				
					
					str-701 (strcat str-01 " IEK, " str-02 ", " str-03)
		);setq
	);if

	(split-str-parts-lecgv-01-general str-701 str-702 str-703 str-99 pnt-ins);
	
	(setq cntr-1 (+ cntr-1 1));setq
);repeat

(princ)
)
;;;;///////////////////////////////////////////////////////////////////////////////////////////////////////////////
;;;;///////////////////////////////////////////////////////////////////////////////////////////////////////////////
