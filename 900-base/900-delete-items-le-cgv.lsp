;/////// ************************************************************ /////////////////////////////////////////////////////////////////////////////////////////////////////////////
;/////// удаление элементов спецификации овш                          /////////////////////////////////////////////////////////////////////////////////////////////////////////////
;/////// ************************************************************ /////////////////////////////////////////////////////////////////////////////////////////////////////////////
(defun 900-delete-items-le-cgv

(nmbr-ln xpnt-ins ypnt-ins / right-bottom st-1)

(setvar "osmode" 0)

(setq right-bottom (+ (* nmbr-ln 8) 2));setq

(setq st-1 (ssget "_c" (list (- xpnt-ins 9.5) (- ypnt-ins 2)) (list (+ xpnt-ins 5.5) (- ypnt-ins 6)));позиция
);setq

(if (= st-1 nil)
	(command "_text" "_MC" (list (- xpnt-ins 7.5) (- ypnt-ins 4)) 2.5 0 "****")
);if

(setq st-1 nil
);setq

(setq st-1 (ssget "_c" (list (+ xpnt-ins 70) (- ypnt-ins 2)) (list (+ xpnt-ins 62) (- ypnt-ins right-bottom)));наименование
);setq

(if (/= st-1 nil)
	(command "_erase" st-1 "")
);if

(setq st-1 nil
);setq

(setq st-1 (ssget "_c" (list (+ xpnt-ins 140.5) (- ypnt-ins 2)) (list (+ xpnt-ins 144.5) (- ypnt-ins 6)));масса
);setq

(if (/= st-1 nil)
	(command "_erase" st-1 "")
);if

(setq st-1 nil
);setq

(setq st-1 (ssget "_c" (list (+ xpnt-ins 128) (- ypnt-ins 2)) (list (+ xpnt-ins 132) (- ypnt-ins 6)));количество
);setq

(if (= st-1 nil)
	(command "_text" "_MC" (list (+ xpnt-ins 130) (- ypnt-ins 4)) 2.5 0 "**")
);if

(setvar "osmode" 0)
(setvar "cmdecho" 0)
(princ)
)
;/////// ************************************************************ /////////////////////////////////////////////////////////////////////////////////////////////////////////////
;///////                                                              /////////////////////////////////////////////////////////////////////////////////////////////////////////////
;/////// ************************************************************ /////////////////////////////////////////////////////////////////////////////////////////////////////////////
