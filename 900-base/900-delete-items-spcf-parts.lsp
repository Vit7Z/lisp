;/////// ************************************************************ /////////////////////////////////////////////////////////////////////////////////////////////////////////////
;/////// удаление составляющих изделия из спецификации                /////////////////////////////////////////////////////////////////////////////////////////////////////////////
;/////// ************************************************************ /////////////////////////////////////////////////////////////////////////////////////////////////////////////
(defun 900-delete-items-spcf-parts

(nmbr-ln pnt-ins / right-bottom st-1 x-pnt-ins y-pnt-ins)

(setvar "osmode" 0)
(setvar "cmdecho" 0)

(setq x-pnt-ins (nth 0 pnt-ins)
	 		y-pnt-ins (nth 1 pnt-ins)
);setq

(setq right-bottom (+ (* nmbr-ln 8) 2)
			st-1 (ssget "_c" (list (+ x-pnt-ins 292) (- y-pnt-ins 10)) (list (+ x-pnt-ins 308) (- y-pnt-ins right-bottom)) '((0 . "*TEXT")))
);setq

(if (/= st-1 nil) (command "_erase" st-1 ""));if

(princ)
)
;/////// ************************************************************ /////////////////////////////////////////////////////////////////////////////////////////////////////////////
;///////                                                              /////////////////////////////////////////////////////////////////////////////////////////////////////////////
;/////// ************************************************************ /////////////////////////////////////////////////////////////////////////////////////////////////////////////
