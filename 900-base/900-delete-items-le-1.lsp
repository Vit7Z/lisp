;/////// ************************************************************ /////////////////////////////////////////////////////////////////////////////////////////////////////////////
;/////// удаление из перечня элементов в графе "наименование",        /////////////////////////////////////////////////////////////////////////////////////////////////////////////
;/////// "примечание"                                                 /////////////////////////////////////////////////////////////////////////////////////////////////////////////
;/////// ************************************************************ /////////////////////////////////////////////////////////////////////////////////////////////////////////////
(defun 900-delete-items-le-1

(nmbr-ln xpnt-ins ypnt-ins / right-bottom st-1)

(setvar "osmode" 0)

(setq right-bottom (+ (* nmbr-ln 8) 2)
			st-1 (ssget "_c" (list (+ xpnt-ins 10) (- ypnt-ins 2)) (list (+ xpnt-ins 2) (- ypnt-ins right-bottom)))
);setq

(if (/= st-1 nil) (command "_erase" st-1 ""));if

(setq st-1 nil);setq

(setq st-1 (ssget "_c" (list (+ xpnt-ins 117) (- ypnt-ins 2)) (list (+ xpnt-ins 113) (- ypnt-ins 6))));setq

(if (= st-1 nil) (command "_text" "_MC" (list (+ xpnt-ins 115) (- ypnt-ins 4)) 2.5 0 "***"));if

(setq st-1 (ssget "_c" (list (+ xpnt-ins 130) (- ypnt-ins 2)) (list (+ xpnt-ins 122) (- ypnt-ins right-bottom))));setq

(if (/= st-1 nil) (command "_erase" st-1 ""));if

(princ)
)
;/////// ************************************************************ /////////////////////////////////////////////////////////////////////////////////////////////////////////////
;///////                                                              /////////////////////////////////////////////////////////////////////////////////////////////////////////////
;/////// ************************************************************ /////////////////////////////////////////////////////////////////////////////////////////////////////////////
