;/////// ************************************************************ /////////////////////////////////////////////////////////////////////////////////////////////////////////////
;/////// удаление элементов спецификации для заголовков спецификации  /////////////////////////////////////////////////////////////////////////////////////////////////////////////
;/////// ************************************************************ /////////////////////////////////////////////////////////////////////////////////////////////////////////////
(defun 900-delete-items-spcf-1

(nmbr-ln xpnt-ins ypnt-ins / right-bottom st-1)

(setvar "osmode" 0)

(setq right-bottom (+ (* nmbr-ln 8) 2));setq

(setq st-1 (ssget "_c" (list (+ xpnt-ins 90) (- ypnt-ins 2)) (list (+ xpnt-ins 2) (- ypnt-ins right-bottom))));setq

(if (/= st-1 nil) (command "_erase" st-1 ""));if

(setq st-1 nil)

(setvar "osmode" 0)
(setvar "cmdecho" 0)

(princ)
)
;/////// ************************************************************ /////////////////////////////////////////////////////////////////////////////////////////////////////////////
;///////                                                              /////////////////////////////////////////////////////////////////////////////////////////////////////////////
;/////// ************************************************************ /////////////////////////////////////////////////////////////////////////////////////////////////////////////
