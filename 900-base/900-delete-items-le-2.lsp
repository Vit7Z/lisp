;/////// ************************************************************ /////////////////////////////////////////////////////////////////////////////////////////////////////////////
;/////// удаление из перечня элементов в графе "количество"           /////////////////////////////////////////////////////////////////////////////////////////////////////////////
;/////// ************************************************************ /////////////////////////////////////////////////////////////////////////////////////////////////////////////
(defun 900-delete-items-le-2

(nmbr-ln xpnt-ins ypnt-ins / right-bottom st-1)

(setvar "osmode" 0)

(setq right-bottom (+ (* nmbr-ln 8) 2));setq

(setq st-1 (ssget "_c" (list (+ xpnt-ins 112) (- ypnt-ins 2)) (list (+ xpnt-ins 118) (- ypnt-ins right-bottom))));setq

;(command "_rectangle" (list (+ xpnt-ins 112) (- ypnt-ins 2)) (list (+ xpnt-ins 118) (- ypnt-ins right-bottom)) (list (+ xpnt-ins 118) (- ypnt-ins right-bottom)))

(if (/= st-1 nil) (command "_erase" st-1 ""));if

(setvar "osmode" 0)
(setvar "cmdecho" 0)

(princ)
)
;/////// ************************************************************ /////////////////////////////////////////////////////////////////////////////////////////////////////////////
;///////                                                              /////////////////////////////////////////////////////////////////////////////////////////////////////////////
;/////// ************************************************************ /////////////////////////////////////////////////////////////////////////////////////////////////////////////
