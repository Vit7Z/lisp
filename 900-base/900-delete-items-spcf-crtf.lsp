;/////// ************************************************************ ////////////////////////////////////////
;/////// удаление сертификата спецификации                            ////////////////////////////////////////
;/////// ************************************************************ ////////////////////////////////////////
(defun 900-delete-items-spcf-crtf

(nmbr-ln pnt-ins / right-bottom st-1 xpnt-ins ypnt-ins)

(setvar "osmode" 0)

(setq xpnt-ins (nth 0 pnt-ins)
	 		ypnt-ins (nth 1 pnt-ins)
	 		
	 		nmbr-ln (- nmbr-ln 1)
	 		right-bottom (+ (* nmbr-ln 8) 2)
);setq

(setq st-1 (ssget "_c" (list (+ xpnt-ins 337) (- ypnt-ins 2)) (list (+ xpnt-ins 345) (- ypnt-ins right-bottom))));setq

(if (/= st-1 nil) (command "_erase" st-1 ""));if

(setvar "osmode" 0)
(setvar "cmdecho" 0)

(princ)
)
;/////// ************************************************************ ////////////////////////////////////////
;///////                                                              ////////////////////////////////////////
;/////// ************************************************************ ////////////////////////////////////////
