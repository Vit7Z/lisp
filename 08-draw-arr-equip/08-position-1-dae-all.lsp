;///////////////////////////////панель инструментов//////////////////////////////////////////////////////
;///////////////////рисование выноски, первого позиционного обозначения//////////////////////////////////
(defun c:08-position-1-dae-all

( / adoc circle-1 drctn-x drctn-y hatch-1 pnt-1 pnt-2 pnt-3 pnt-ins pnt-txt ss1 xpnt-2 xpnt-ins ypnt-2 ypnt-ins)

(vl-load-com)

(vla-startundomark 
	(setq adoc (vla-get-activedocument (vlax-get-acad-object)))
);undo

(setvar "cmdecho" 0)
(setvar "osmode" 0)
(setvar "celweight" -1)

(if (= (tblsearch "layer" "arngment-equip") nil)
	(entmakex 
		'((0 . "LAYER")
  	(100 . "AcDbSymbolTableRecord")
  	(100 . "AcDbLayerTableRecord")
  	(2 . "arngment-equip")
  	(70 . 0) ;standard flags (bit-coded values): 1 = Layer is frozen
  	(62 . 152) ;color
  	(6 . "Continuous") ;linetype name
  	(290 . 1) ;plotting flag. If set to 0, do not plot this layer
  	(370 . -1)) ;lineweight enum value; line wide 0
	);entmakex
);if

(setvar "clayer" "arngment-equip")

(if (= (tblsearch "block" "точка-1мм" ) nil)
	(progn
	  (command "_circle" '(0 0 ) 0.5)
	  (setq circle-1 (entlast))
	  (command "_hatch" "solid" circle-1 "")
	  (setq hatch-1 (entlast))
	  (command "_block" "точка-1мм" '(0 0 ) circle-1 hatch-1 "")
	);progn
);if

(setvar "osmode" 0)
(setvar "orthomode" 0)

(setq pnt-1 (getpoint "\nУкажите точку 1\n")
      ss1 (ssadd) ;пустой набор, для линий
);setq

(command "_insert" "точка-1мм" "_X" 1 "_Y" 1 "_Z" 1 "_R" 0 pnt-1)

(setvar "osmode" 6199)

(while (/= (setq pnt-2 (getpoint "\nУкажите точку 2\n")) nil)
	(setq xpnt-2 (nth 0 pnt-2)
		  	ypnt-2 (nth 1 pnt-2)
	);setq
	
	(setvar "osmode" 0)
	(command "_line" pnt-1 pnt-2 "")
	
	(setq ss1 (ssadd (entlast) ss1));setq
	
	(setvar "osmode" 6199)
	(setq pnt-1 pnt-2);setq
);while

(if	(= pnt-2 nil)
  (setq pnt-2 pnt-1);setq
);if

(setq	pnt-ins (getpoint "\nУкажите направление полки\n") ;первая точка выноски 
      xpnt-ins (nth 0 pnt-ins)
      ypnt-ins (nth 1 pnt-ins)
      drctn-x (- xpnt-ins xpnt-2);направление вставки, гориз
			drctn-y (- ypnt-ins ypnt-2);направление вставки, верт
);setq

(if (> drctn-x 0)

	(progn ;полка вправо
		(setq pnt-3 (list (+ xpnt-2 6) ypnt-2); конечня точка полки
      		pnt-txt (list (+ xpnt-2 3) ypnt-2)
		);setq
	);progn

	(progn ;полка влево
		(setq pnt-3 (list (- xpnt-2 6) ypnt-2); конечня точка полки
      		pnt-txt (list (- xpnt-2 3) ypnt-2)
		);setq
	);progn
);if

(setvar "osmode" 0)
(command "_line" pnt-2 pnt-3 "")
(setq ss1 (ssadd (entlast) ss1));setq

(setvar 'PEDITACCEPT 1)
(command "_pedit" "_M" ss1 "" "_J" "" "")
(setvar 'PEDITACCEPT 0)

(command "_TEXT" "_BC" pnt-txt 3 0 "***")

(setvar "osmode" 6199)
(setvar "cmdecho" 1)
(setvar "clayer" "0")

(vla-endundomark adoc)

(princ)
(gc)
)
;///////////////////////////////////// конец программы ///////////////////////////////////
