;/////// ************************************************************ ///////////////////////////////////////////////////////////////////////////////////////////////////////////
;///////                                                              ///////////////////////////////////////////////////////////////////////////////////////////////////////////
;/////// ************************************************************ ///////////////////////////////////////////////////////////////////////////////////////////////////////////
(defun 101-01-plc-s7-1200

( / adoc dcl-id list-01 list-01-read-file list-02 list-02-read-file list-03 list-03-read-file list-04 list-04-read-file list-801 list-802 list-900 list-901 list-902 list-99 str-01 type-list)

(vl-load-com)
(vla-startundomark (setq adoc (vla-get-activedocument (vlax-get-acad-object))));start undo

(read-file-for-dialog-box-01 "101-01-plc-s7-1200-01-general.txt" 3)

(setq str-01 "0"
			list-901 nil
			list-902 nil
			list-04-read-file nil

			list-01 list-01-read-file
			list-801 list-02-read-file
			list-802 list-03-read-file
);setq

(txt-01-101-01-plc-s7-1200 str-01)

(if (< (setq dcl-id (load_dialog "dia-101-01-plc-s7-1200.dcl")) 0) ;ищем диалог
	(progn
		(alert "Не найден dcl-файл")
		(exit)
	);progn
);if

(if (not (new_dialog "dia_101_01_plc_s7_1200" dcl-id))
	(exit)
);if

(list-filling "txt-01" list-01)
(list-filling "txt-02" list-02)
(list-filling "txt-03" list-03)
(list-filling "txt-04" list-04)
(list-filling "txt-99" list-99)
(list-filling "txt-900" list-900)

(set_tile "txt-01" "0")
(set_tile "txt-02" "0")
(set_tile "txt-03" "0")
(set_tile "txt-04" "0")
(set_tile "txt-99" "0")

(action_tile "txt-01"
  (strcat "(setq str-01 (get_tile \"txt-01\"))"
  				"(txt-01-101-01-plc-s7-1200 str-01)"
  );srcat
);action_tile

(action_tile "txt-02"
  (strcat "(setq str-02 (get_tile \"txt-02\"))"
  				"(txt-02-101-01-plc-s7-1200 str-02)"
  );srcat
);action_tile

(action_tile "txt-03"
  (strcat "(set_tile \"txt-02\" $value)"
  			 	"(set_tile \"txt-04\" $value)"
  );srcat
);action_tile

(action_tile "but1"
  (strcat "(but1-101-01-plc-s7-1200)");srcat
);action_tile

(action_tile "but2"
  (strcat "(setq type-list \"le\")"
          "(done_dialog)"
  );strcat
);action_tile

(action_tile "but3"
  (strcat "(setq type-list \"spcf\")"
          "(done_dialog)"
  );strcat
);action_tile

(action_tile "but4"
  (strcat "(setq type-list \"lecgv\")"
          "(done_dialog)"
  );strcat
);action_tile

(action_tile "accept"
  (strcat "(done_dialog)"
          "(exit)"
  );strcat
);action_tile

(start_dialog)
(unload_dialog dcl-id)

(cond
	((= type-list "le") (le-101-01-plc-s7-1200));=
	((= type-list "spcf") (spcf-101-01-plc-s7-1200));=
	((= type-list "lecgv") (lecgv-101-01-plc-s7-1200));=
);cond

(setvar "osmode" 6199)
(setvar "cmdecho" 1)
(vla-endundomark adoc)
(gc)
(princ)
)
;;;;/////////////////////////////////////////////////////////////////////////////////////////////////////////////////////////////////////////////////////////////////////////////
;/////// конец программы ////////////////////////////////////////////////////////////////////////////////////////////////////////////////////////////////////////////////////////


;;;;/////////////////////////////////////////////////////////////////////////////////////////////////////////////////////////////////////////////////////////////////////////////
;;;;/////////////////////////////////////////////////////////////////////////////////////////////////////////////////////////////////////////////////////////////////////////////
(defun txt-01-101-01-plc-s7-1200

(str-01 / list-01-read-file list-02-read-file list-03-read-file list-04-read-file list-900-dscr list-900-menu name-file-1 num-flds)

(setq name-file-1 (nth (atoi str-01) list-801)
			num-flds (atoi (nth (atoi str-01) list-802))
);setq

(read-file-for-dialog-box-01 name-file-1 num-flds)

(set_tile "ml-31" (nth 0 list-900-menu))
(set_tile "ml-32" (nth 1 list-900-menu))
(set_tile "ml-41" (nth 2 list-900-menu))
(set_tile "ml-42" (nth 3 list-900-menu))

(setq list-02 list-01-read-file
			list-03 list-02-read-file
			list-04 list-03-read-file
			list-99 list-04-read-file
			list-900 list-900-dscr
);setq

(if (/= list-900 nil) 
	(divide-text-into-parts list-900 26)
);if

(list-filling "txt-02" list-02)
(list-filling "txt-03" list-03)
(list-filling "txt-04" list-04)
(list-filling "txt-05" list-05)
(list-filling "txt-99" list-99)
(list-filling "txt-900" list-900)

(set_tile "txt-02" "0")
(set_tile "txt-03" "0")
(set_tile "txt-04" "0")
(set_tile "txt-99" "0")

(princ)
)
;;;;/////////////////////////////////////////////////////////////////////////////////////////////////////////////////////////////////////////////////////////////////////////////
;;;;/////////////////////////////////////////////////////////////////////////////////////////////////////////////////////////////////////////////////////////////////////////////


;;;;/////////////////////////////////////////////////////////////////////////////////////////////////////////////////////////////////////////////////////////////////////////////
;;;;/////////////////////////////////////////////////////////////////////////////////////////////////////////////////////////////////////////////////////////////////////////////
(defun txt-02-101-01-plc-s7-1200

(str-02 / list-900-read-file)

(set_tile "txt-03" str-02)
(set_tile "txt-04" str-02)


(princ)
)
;;;;/////////////////////////////////////////////////////////////////////////////////////////////////////////////////////////////////////////////////////////////////////////////
;;;;/////////////////////////////////////////////////////////////////////////////////////////////////////////////////////////////////////////////////////////////////////////////


;;;;/////////////////////////////////////////////////////////////////////////////////////////////////////////////////////////////////////////////////////////////////////////////
;;;;подпрограмма формирования данных/////////////////////////////////////////////////////////////////////////////////////////////////////////////////////////////////////////////
(defun but1-101-01-plc-s7-1200

( / str-01 str-02 str-03 str-04 str-99 str-chnls str-prfx tmp-str-902)

(setq str-01 (nth (atoi (get_tile "txt-01")) list-01)
			str-02 (nth (atoi (get_tile "txt-02")) list-02)
			str-03 (nth (atoi (get_tile "txt-03")) list-03)
			str-04 (nth (atoi (get_tile "txt-04")) list-04)
			str-99 (nth (atoi (get_tile "txt-99")) list-99)
			str-prfx "S7-1200"
			str-chnls "каналов"
);setq

(if (or (= str-03 "4") (= str-03 "32") (= str-03 "24"))
	(setq str-chnls "канала"
	);setq
);if

(if (/= list-901 nil) 
	(setq list-901 (reverse list-901)
				list-902 (reverse list-902)
	);setq
);if

;;;;;;;;////////////////////////////////
(if (= str-01 "Процессор")
	(setq list-901 (vl-list* (strcat str-02 "  Uпит. " str-03 "  " str-04) list-901)
				tmp-str-902 (list (cons 1 str-01) 
													(cons 2 (strcat str-prfx " " str-02)) 
													(cons 3 str-04) 
													(cons 99 str-99))	
	);setq
);if

;;;;;;;;////////////////////////////////
(if (or (= str-01 "Модуль A-in")
		  	(= str-01 "Модуль A-out")
		  	(= str-01 "Модуль D-in")
		  	(= str-01 "Модуль D-out"));or
	
	(setq list-901 (vl-list* (strcat str-01 "  " str-02 "  " str-03 " " str-chnls " (" str-04 ")") list-901)
				tmp-str-902 (list (cons 1 str-01)
													(cons 2 (strcat str-prfx " " str-02)) 
													(cons 3 (strcat str-03 " " str-chnls " (" str-04 ")"))
													(cons 99 str-99))
	);setq
);if

;;;;;;;;////////////////////////////////
(if (= str-01 "Карта памяти")
	(setq list-901 (vl-list* (strcat str-01 "  " str-02 "  Объем " str-03) list-901)
				tmp-str-902 (list (cons 1 str-01) 
													(cons 2 str-02) 
													(cons 3 str-03) 
													(cons 99 str-99))
	);setq
);if

;;;;;;;;////////////////////////////////
(if (= str-01 "Модуль коммуникационный")
	(setq list-901 (vl-list* (strcat str-01 "  " str-02 "  " str-04) list-901)
				tmp-str-902 (list (cons 1 str-01) 
													(cons 2 (strcat str-prfx " " str-02)) 
													(cons 3 str-04) 
													(cons 99 str-99))
	);setq
);if

(setq list-902 (vl-list* tmp-str-902 list-902)
			list-901 (reverse list-901)
			list-902 (reverse list-902)
);setq

(list-filling "txt-901" list-901)

(princ)
)
;;;;////////////////////////////////////////////////////////////////////////////////////////////////////////////////////////////////////////////////////////////////////////////
;;;;////////////////////////////////////////////////////////////////////////////////////////////////////////////////////////////////////////////////////////////////////////////


;;;;////////////////////////////////////////////////////////////////////////////////////////////////////////////////////////////////////////////////////////////////////////////
;;;;подпрограмма вывода в ПЭ                   /////////////////////////////////////////////////////////////////////////////////////////////////////////////////////////////////
(defun le-101-01-plc-s7-1200

( / cntr-1 pnt-ins str-01 str-02 str-03 str-701 str-702 str-tmp)

(setq cntr-1 0);setq

(repeat (length list-902)
	(setq str-tmp (nth cntr-1 list-902)
				str-01 (cdr (assoc 1 str-tmp))
				str-02 (cdr (assoc 2 str-tmp))
				str-03 (cdr (assoc 3 str-tmp))
	);setq
	
;(princ "\n         str-tmp = ") (princ str-tmp);Erase_DV
;(getstring "\nPress Enter to continue...");Erase_DV

	(setvar "osmode" 6199)
	
	(setq pnt-ins (getpoint "\nУкажите точку вставки\n"));setq
	
	;///////////////////////////////////////////////////////////////////
	(if (= str-01 "Процессор")
		(setq str-701 (strcat "Процессор " str-02 ", " str-03));setq
	);if

	;///////////////////////////////////////////////////////////////////
	(if (= str-01 "Модуль A-in")				
		(setq str-701 (strcat "Модуль ввода аналоговых сигналов " str-02 ", " str-03));setq
	);if

	;///////////////////////////////////////////////////////////////////
	(if (= str-01 "Модуль A-out")				
		(setq str-701 (strcat "Модуль вывода аналоговых сигналов " str-02 ", " str-03));setq
	);if
	
	;///////////////////////////////////////////////////////////////////
	(if (= str-01 "Модуль D-in")				
		(setq str-701 (strcat "Модуль ввода дискретных сигналов " str-02 ", " str-03));setq
	);if
	
	;///////////////////////////////////////////////////////////////////
	(if (= str-01 "Модуль D-out")				
		(setq str-701 (strcat "Модуль вывода дискретных сигналов " str-02 ", " str-03));setq
	);if
	
	;///////////////////////////////////////////////////////////////////
	(if (= str-01 "Модуль коммуникационный")				
		(setq str-701 (strcat str-01 " " str-02 ", " str-03));setq
	);if
		
	;///////////////////////////////////////////////////////////////////
	(if (= str-01 "Карта памяти")				
		(setq str-701 (strcat str-01 " " str-02 ", объем " str-03));setq
	);if

	
	(split-str-parts-le-01-general str-701 str-702 pnt-ins "**1**");
	
	(setq str-702 nil
				cntr-1 (1+ cntr-1)
	);setq
);repeat

(princ)
)
;;;;///////////////////////////////////////////////////////////////////////////////////////////////////////////////////////////////////////////////////////////////////////////
;;;;///////////////////////////////////////////////////////////////////////////////////////////////////////////////////////////////////////////////////////////////////////////

;;;;////////////////////////////////////////////////////////////////////////////////////////////////////////////////////////////////////////////////////////////////////////////
;;;;подпрограмма вывода в спцф                   ///////////////////////////////////////////////////////////////////////////////////////////////////////////////////////////////
(defun spcf-101-01-plc-s7-1200

( / cntr-1 dlt-y nmbr-ln pnt-ins str-01 str-02 str-03 str-04 str-99 str-lft-02 str-lft-03 str-tmp x-pnt-ins y-pnt-ins y-pnt-ins-1)

(setq cntr-1 0);setq

(repeat (length list-902)
	(setq str-tmp (nth cntr-1 list-902)
				str-01 (cdr (assoc 1 str-tmp))
				str-02 (cdr (assoc 2 str-tmp))
				str-03 (cdr (assoc 3 str-tmp))
				str-04 (cdr (assoc 4 str-tmp))
				str-99 (cdr (assoc 99 str-tmp))
	);setq

	(setvar "osmode" 6199)
	
	(setq pnt-ins (getpoint "\nУкажите точку вставки\n")
	
	
	
	
	
	);setq



	(repeat nmbr-ln
  	(command "_insert" "зс-пустая-строка" "_X" 1 "_Y" 1 "_Z" 1 "_R" 0 (list x-pnt-ins y-pnt-ins-1))
  	(setq y-pnt-ins-1 (- y-pnt-ins-1 8));setq
	);repeat
								
	(command "_text" "_MC" (list (+ x-pnt-ins 247.5) (- (- y-pnt-ins (* dlt-y 0)) 4)) 2.5 0 "\"Siemens\", г. Москва")
 
	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////


;;;;////////////////////////////////////////////////////////////////////////////////////////////////////////////////////////////////////////////////////////////////////////////
;;;;подпрограмма вывода в овш               ////////////////////////////////////////////////////////////////////////////////////////////////////////////////////////////////////
(defun lecgv-101-01-plc-s7-1200

( / cntr-1 pnt-ins str-01 str-02 str-03 str-701 str-702 str-703 str-99 str-tmp)

(setq cntr-1 0);setq

(repeat (length list-902)	
	(setvar "osmode" 6199)
	
	(setq pnt-ins (getpoint "\nУкажите точку вставки\n")
	
				str-tmp (nth cntr-1 list-902)
				str-01 (cdr (assoc 1 str-tmp))
				str-02 (cdr (assoc 2 str-tmp))
				str-03 (cdr (assoc 3 str-tmp))
				str-99 (cdr (assoc 99 str-tmp))
	);setq
	
;(princ "\n         str-tmp = ") (princ str-tmp);Erase_DV
;(getstring "\nPress Enter to continue...");Erase_DV
	
	
	;///////////////////////////////////////////////////////////////////
	(if (= str-01 "Контроллер")
		(setq str-701 (strcat "Контроллер " str-02 ", " str-03));setq
	);if

	;///////////////////////////////////////////////////////////////////
	(if (= str-01 "Модуль A-in")				
		(setq str-701 (strcat "Модуль ввода аналоговых сигналов " str-02 ", " str-03));setq
	);if

	;///////////////////////////////////////////////////////////////////
	(if (= str-01 "Модуль A-out")				
		(setq str-701 (strcat "Модуль вывода аналоговых сигналов " str-02 ", " str-03));setq
	);if
	
	;///////////////////////////////////////////////////////////////////
	(if (= str-01 "Модуль D-in")				
		(setq str-701 (strcat "Модуль ввода дискретных сигналов " str-02 ", " str-03));setq
	);if
	
	;///////////////////////////////////////////////////////////////////
	(if (= str-01 "Модуль D-out")				
		(setq str-701 (strcat "Модуль вывода дискретных сигналов " str-02 ", " str-03));setq
	);if

	;///////////////////////////////////////////////////////////////////
	(if (= str-01 "Модуль коммуникационный")				
		(setq str-701 (strcat str-01 " " str-02 ", " str-03));setq
	);if

	;///////////////////////////////////////////////////////////////////
	(if (= str-01 "Карта памяти")				
		(setq str-701 (strcat str-01 " " str-02 ", объем " str-03));setq
	);if


	;;;;;;;;;/////////
	(setq str-702 nil
				str-703 nil
	);setq

	(split-str-parts-lecgv-01-general str-701 str-702 str-703 str-99 pnt-ins);
 
	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////
