;///////// рисование подвала (таблицы) для схемы электропитания по трем точкам крайняя левая, нижняя, ркрайняя правая
(defun c:04-cap-tble-seb

( / adoc crnt-color pnt-1-rctgl pnt-2-rctgl pnt-ins-1 pnt-ins-2 pnt-ins-3 pnt-txt txt-2 x-dlt x-dlt-mtxt x-lft x-mdl-txt x-rght y-top)

(setvar "cmdecho" 0)
(setvar "osmode" 6199)
	
(vl-load-com)
(vla-startundomark (setq adoc (vla-get-activedocument (vlax-get-acad-object))));start undo

(setq crnt-color (getvar "cecolor")

			pnt-ins-1 (getpoint "\nУкажите крайнюю левую точку\n")
			
			pnt-ins-2 (getpoint "\nУкажите крайнюю нижнюю точку\n")
			
			pnt-ins-3 (getpoint "\nУкажите крайнюю правую точку\n")			
			
			x-dlt (getint "\nУкажите расстояние\n")
			
			x-lft (nth 0 pnt-ins-1) ;крайняя левая координата для прямоугольника
			
			x-rght (nth 0 pnt-ins-3)	;крайняя правая координата для прямоугольника
				
			y-top (nth 1 pnt-ins-2)
);setq

(if (= x-dlt nil)
	(setq x-dlt 0)
);if

(setq x-lft (- x-lft x-dlt)

			x-rght (+ x-rght x-dlt)
			
			x-mdl-txt (+ x-lft (* (- x-rght x-lft) 0.5)) ;координата середины однострочноготекста
			
			x-dlt-mtxt (- (- x-rght x-lft) 1) ;половина ширины для многострочноготекста
);setq

(setvar "osmode" 0)

(setvar "textsize" 2.5)

(setvar "celtype" "ByLayer")

;определяем точки прямоуголника 1
(setq pnt-1-rctgl	(list x-lft y-top)
			pnt-2-rctgl	(list x-rght (- y-top 8))
			
			pnt-txt (list x-mdl-txt (- y-top 4))
);setq

;рисуем прямоугольник 1
(command "_rectangle" pnt-1-rctgl pnt-2-rctgl)

(command "_text" "_mc" pnt-txt 2.5 0 "***1")

;определяем точки прямоуголника 2
(setq pnt-1-rctgl	(list x-lft (- y-top 8))
			pnt-2-rctgl	(list x-rght (- y-top 42))
			
			pnt-txt (list x-mdl-txt (- y-top 25))
);setq

;рисуем прямоугольник 2
(command "_rectangle" pnt-1-rctgl pnt-2-rctgl)

(setq txt-2
  (entmakex
    (list
      '(0 . "MTEXT")
      '(100 . "AcDbEntity")
      '(100 . "AcDbMText")
      (cons 10 pnt-txt) 
      '(1 . "***2") 
      '(8 . "0")
      '(40 . 2.5) 
      (cons 41 x-dlt-mtxt) 
      (cons 42 x-dlt-mtxt) 
      '(71 . 5) 
      '(370 . -1) 
       (cons 7 (getvar "textstyle")) 
    );list
  );entmakex
);setq

;определяем точки прямоуголника 3
(setq pnt-1-rctgl	(list x-lft (- y-top 42))
			pnt-2-rctgl	(list x-rght (- y-top 50))
			
			pnt-txt (list x-mdl-txt (- y-top 46))
);setq

;рисуем прямоугольник 3
(command "_rectangle" pnt-1-rctgl pnt-2-rctgl)

(command "_text" "_mc" pnt-txt 2.5 0 "***В")

;определяем точки прямоуголника 4
(setq pnt-1-rctgl	(list x-lft (- y-top 50))
			pnt-2-rctgl	(list x-rght (- y-top 58))
			
			pnt-txt (list x-mdl-txt (- y-top 54))
);setq

;рисуем прямоугольник 4
(command "_rectangle" pnt-1-rctgl pnt-2-rctgl)

(command "_text" "_mc" pnt-txt 2.5 0 "***4")

(vla-endundomark adoc)

(setvar "osmode" 6199)
(setvar "cmdecho" 1)

(princ)
)
;//////////////////////// конец программы ///////////////////////////////////////
