;;; ///////////////////////////////////////////////// оформление перечня элементов ///////////////////////
(defun c:101-00-spcf-sections

( / adoc box-txt dcl-id list-01 list-01-read-file list-02 nmbr-ln p21-c p22-c pnt-ins scale-len-txt txt-01 xpnt-ins ypnt-ins)

(vl-load-com)

(vla-startundomark (setq adoc (vla-get-activedocument (vlax-get-acad-object))));start undo

(setvar "cmdecho" 0)

(setvar "textstyle" "standard")

(101-00-spcf-empty-line)

(read-file-for-dialog-box-01 "101-00-spcf-sections-std.txt" 1);setq

(setq list-01 list-01-read-file);setq

(read-file-for-dialog-box-01 "101-00-spcf-sections-dif.txt" 1);setq

(setq list-02 list-01-read-file);setq

(if (< (setq dcl-id (load_dialog "dia-101-00-spcf-sections.dcl")) 0) ;ищем диалог
		(progn
			(alert "Не найден dcl-файл")
			(exit)
		);progn
);if

(if (not (new_dialog "dia_101_spcf_auto" dcl-id))
		(exit)
);if

(list-filling "txt-01" list-01)
(list-filling "txt-02" list-02)

(action_tile "txt-01"
  (strcat "(setq txt-01 (nth (atoi (get_tile \"txt-01\")) list-01))"
  				"(done_dialog)"
  );strcat
);action_tile

(action_tile "txt-02"
  (strcat "(setq txt-01 (nth (atoi (get_tile \"txt-02\")) list-02))"
  				"(done_dialog)"
  );strcat
);action_tile

(action_tile "accept"
  (strcat "(done_dialog)"
          "(exit)"
  );strcat
);action_tile

(start_dialog)
(unload_dialog dcl-id)

(if (= txt-01 "ТЕХ. СРЕДСТВА СА ПОСТАВЛЯЕМЫЕ ...")
	(setq txt-01 "ТЕХНИЧЕСКИЕ СРЕДСТВА АВТОМАТИЗЦИИ, ПОСТАВЛЯЕМЫЕ КОМПЛЕКТНО С ОБОРУДОВАНИЕМ");setq
);if

(setq	box-txt (textbox (list (cons 1 txt-01) (cons 40 2.5) (cons 50 0) (cons 41 1)));определяем длину текста
			p21-c (car (nth 0 box-txt))
			p22-c (car (nth 1 box-txt))
			scale-len-txt (- p22-c p21-c);длина текста
			
			nmbr-ln (fix (/ scale-len-txt 128))
);setq

(setvar "osmode" 6199)

(setq	pnt-ins (getpoint "\nУкажите точку вставки\n")
			xpnt-ins (nth 0 pnt-ins)
			ypnt-ins (nth 1 pnt-ins)
);setq

(if (= nmbr-ln 0)
	(progn
		(del-str-101-00-spcf-sections 3 xpnt-ins ypnt-ins)		
		(command "_TEXT" "_MC" (list (+ xpnt-ins 65) (- ypnt-ins 12)) 2.5 0 (strcat "%%U" txt-01))
	);progn
);if

(if (= nmbr-ln 1)
	(progn
		(del-str-101-00-spcf-sections 4 xpnt-ins ypnt-ins)		
		(str-2-101-00-spcf-sections txt-01 xpnt-ins ypnt-ins)
	);progn
);if

(vla-endundomark adoc)

(setvar "osmode" 6199)
(setvar "cmdecho" 1)
(gc)
(princ)
)
;/////// *************************************************************//////////////////////////////////////////////////////////////////////////////////////////
;/////// КОНЕЦ ПРОГРАММЫ                                              //////////////////////////////////////////////////////////////////////////////////////////
;/////// *************************************************************//////////////////////////////////////////////////////////////////////////////////////////


;/////// ************************************************************ //////////////////////////////////////////////////////////////////////////////////////////
;///////                                                              //////////////////////////////////////////////////////////////////////////////////////////
(defun del-str-101-00-spcf-sections

(nmbr-ln xpnt-ins ypnt-ins / st-1)

(setvar "osmode" 0)

;;;;;;; удаляем существующую надпись
(repeat nmbr-ln
	(setq st-1 (ssget "_c" (list (+ xpnt-ins 108) (- ypnt-ins 2)) (list (+ xpnt-ins 2) (- ypnt-ins 6))));setq, выбираем текст
	
	(if (/= st-1 nil) (command "_erase" st-1 ""));if удаляем текст
	
	(setq st-1 nil
				st-1 (ssget "_c" (list (+ xpnt-ins 1) (- ypnt-ins 7)) (list (- xpnt-ins 1) (- ypnt-ins 1))) ;;;;;;;выбираем линии
	);setq, строки ПЭ
	
	(if (/= st-1 nil) (command "_erase" st-1 ""));if удаляем линии
	
	(command "_insert" "зс-пустая-строка" "_X" 1 "_Y" 1 "_Z" 1 "_R" 0 (list xpnt-ins ypnt-ins))
	
	(setq ypnt-ins (- ypnt-ins 8));setq
);repeat

(princ)
)
;///////                                                              //////////////////////////////////////////////////////////////////////////////////////////
;/////// ************************************************************ //////////////////////////////////////////////////////////////////////////////////////////


;/////// ************************************************************ //////////////////////////////////////////////////////////////////////////////////////////
;///////                                                              //////////////////////////////////////////////////////////////////////////////////////////
(defun str-2-101-00-spcf-sections 

(txt-01 xpnt-ins ypnt-ins / txt-l txt-r)

(setvar "osmode" 0)

(if (= txt-01 "ТЕХНИЧЕСКИЕ СРЕДСТВА АВТОМАТИЗЦИИ, ПОСТАВЛЯЕМЫЕ КОМПЛЕКТНО С ОБОРУДОВАНИЕМ")
	(setq txt-l "%%UТЕХНИЧЕСКИЕ СРЕДСТВА АВТОМАТИЗЦИИ,"
				txt-r "%%uПОСТАВЛЯЕМЫЕ КОМПЛЕКТНО С ОБОРУДОВАНИЕМ"
	);setq
);if

(command "_TEXT" "_MC" (list (+ xpnt-ins 65) (- ypnt-ins 12)) 2.5 0 txt-l)

(command "_TEXT" "_MC" (list (+ xpnt-ins 65) (- ypnt-ins 20)) 2.5 0 txt-r)

(princ)
)
;///////                                                              //////////////////////////////////////////////////////////////////////////////////////////
;/////// ************************************************************ //////////////////////////////////////////////////////////////////////////////////////////
