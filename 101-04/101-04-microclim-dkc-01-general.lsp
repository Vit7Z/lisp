;/////// ************************************************************ ///////////////////////////////////////////////////////////////////////////////////////////////////////////
;///////                                                              ///////////////////////////////////////////////////////////////////////////////////////////////////////////
;/////// ************************************************************ ///////////////////////////////////////////////////////////////////////////////////////////////////////////
(defun 101-04-microclim-dkc-01-general

( / adoc dcl-id list-01 list-01-read-file list-02 list-02-read-file list-03 list-03-read-file list-04 list-05 list-06 list-07 list-801 list-802 list-900 list-901 list-902 str-01 type-list)

(vl-load-com)
(vla-startundomark (setq adoc (vla-get-activedocument (vlax-get-acad-object))));start undo

(setq	list-901 nil
      list-902 nil
      list-900 nil
      
			str-01 "0"
);setq

(read-file-for-dialog-box-01 "101-04-microclim-dkc-01-general.txt" 3)

(setq list-01 list-01-read-file
			list-801 list-02-read-file
			list-802 list-03-read-file
);setq

(start-101-04-microclim-dkc-01-general str-01)

(if (< (setq dcl-id (load_dialog "dia-101-04-microclim-dkc-01-general.dcl")) 0) ;ищем диалог
	(progn
		(alert "Не найден dcl-файл")
		(exit)
	);progn
);if

(if (not (new_dialog "dia_101_04_microclim_dkc_01_general" dcl-id))
	(exit)
);if

(list-filling "txt-01" list-01)
(list-filling "txt-02" list-02)
(list-filling "txt-03" list-03)
(list-filling "txt-04" list-04)
(list-filling "txt-05" list-05)
(list-filling "txt-06" list-06)
(list-filling "txt-900" list-900)

(set_tile "txt-01" "0")
(set_tile "txt-02" "0")
(set_tile "txt-03" "0")
(set_tile "txt-04" "0")
(set_tile "txt-05" "0")
(set_tile "txt-06" "0")

(action_tile "txt-01"
  (strcat "(setq str-01 (get_tile \"txt-01\"))"
  				"(start-101-04-microclim-dkc-01-general str-01)");srcat
);action_tile

(action_tile "txt-02"
  (strcat "(set_tile \"txt-03\" $value)"
          "(set_tile \"txt-04\" $value)"
          "(set_tile \"txt-05\" $value)"    
          "(set_tile \"txt-06\" $value)"     
  );srcat
);action_tile

(action_tile "txt-03"
  (strcat "(set_tile \"txt-01\" $value)"
          "(set_tile \"txt-02\" $value)"
          "(set_tile \"txt-04\" $value)"
          "(set_tile \"txt-05\" $value)"   
          "(set_tile \"txt-06\" $value)"      
  );srcat
);action_tile

(action_tile "txt-04"
  (strcat "(set_tile \"txt-01\" $value)"
          "(set_tile \"txt-02\" $value)"
          "(set_tile \"txt-03\" $value)"
          "(set_tile \"txt-05\" $value)"   
          "(set_tile \"txt-06\" $value)"      
  );srcat
);action_tile

(action_tile "txt-05"
  (strcat "(set_tile \"txt-01\" $value)"
          "(set_tile \"txt-02\" $value)"
          "(set_tile \"txt-03\" $value)"
          "(set_tile \"txt-04\" $value)" 
          "(set_tile \"txt-06\" $value)"        
  );srcat
);action_tile

(action_tile "txt-06"
  (strcat "(set_tile \"txt-01\" $value)"
          "(set_tile \"txt-02\" $value)"
          "(set_tile \"txt-03\" $value)"
          "(set_tile \"txt-04\" $value)" 
          "(set_tile \"txt-05\" $value)"        
  );srcat
);action_tile

(action_tile "but1"
  (strcat "(filling-fields-101-04-microclim-dkc-01-general)");strcat
);action_tile

(action_tile "but2"
  (strcat "(setq type-list \"le\")"
          "(done_dialog)"
  );strcat
);action_tile

(action_tile "but3"
  (strcat "(setq type-list \"spcf\")"
          "(done_dialog)"
  );strcat
);action_tile

(action_tile "but4"
  (strcat "(setq type-list \"lecgv\")"
          "(done_dialog)"
  );strcat
);action_tile

(action_tile "but5"
  (strcat "(list-delete-item)");strcat
);action_tile

(action_tile "accept"
  (strcat "(done_dialog)"
          "(exit)"
  );strcat
);action_tile

(start_dialog)
(unload_dialog dcl-id)

(cond
	((= type-list "le") (le-101-04-microclim-dkc-01-general list-902));=
	((= type-list "spcf") (spcf-101-04-microclim-dkc-01-general list-902));=
	((= type-list "lecgv") (lecgv-101-04-microclim-dkc-01-general list-902));=
);cond

(setvar "osmode" 6199)
(setvar "cmdecho" 1)
(vla-endundomark adoc)
(princ)
)
;/////// конец программы ///////

;;;;///////////////////////////////////////////////////////////////////////////////////////////////////////////////
;;;;///////////////////////////////////////////////////////////////////////////////////////////////////////////////
(defun start-101-04-microclim-dkc-01-general

(str-01 / list-01-read-file list-02-read-file list-03-read-file list-04-read-file list-05-read-file 
list-06-read-file list-900-dscr list-900-menu list-900-read-file name-file-1 num-flds)

(setq name-file-1 (nth (atoi str-01) list-801)
			num-flds (atoi (nth (atoi str-01) list-802))
);setq

;;;;;;;интерфейс
(read-file-for-dialog-box-01 name-file-1 num-flds)

(set_tile "ml-31" (nth 0 list-900-menu))
(set_tile "ml-32" (nth 1 list-900-menu))
(set_tile "ml-33" (nth 2 list-900-menu))

(set_tile "ml-41" (nth 3 list-900-menu))
(set_tile "ml-42" (nth 4 list-900-menu))
(set_tile "ml-43" (nth 5 list-900-menu))

(set_tile "ml-51" (nth 6 list-900-menu))
(set_tile "ml-52" (nth 7 list-900-menu))
(set_tile "ml-53" (nth 8 list-900-menu))

(set_tile "ml-61" (nth 9 list-900-menu))
(set_tile "ml-62" (nth 10 list-900-menu))
(set_tile "ml-63" (nth 11 list-900-menu))

(setq list-02 list-01-read-file
			list-03 list-02-read-file
			list-04 list-03-read-file
			list-05 list-04-read-file
			list-06 list-05-read-file
);setq

(divide-text-into-parts list-900-dscr 178)

(setq list-900 list-900-read-file);setq

(list-filling "txt-02" list-02)
(list-filling "txt-03" list-03)
(list-filling "txt-04" list-04)
(list-filling "txt-05" list-05)
(list-filling "txt-06" list-06)
(list-filling "txt-900" list-900)

(set_tile "txt-02" "0")
(set_tile "txt-03" "0")
(set_tile "txt-04" "0")
(set_tile "txt-05" "0")
(set_tile "txt-06" "0")

(princ)
)
;;;;///////////////////////////////////////////////////////////////////////////////////////////////////////////////
;;;;///////////////////////////////////////////////////////////////////////////////////////////////////////////////


;;;;///////////////////////////////////////////////////////////////////////////////////////////////////////////////
;;;;подпрограмма формирования данных///////////////////////////////////////////////////////////////////////////////
(defun filling-fields-101-04-microclim-dkc-01-general

( / str-01 str-02 str-03 str-04 str-05 str-06 str-99 tmp-902)

;;;;;;; str-98 - ед. измерения

(setq str-01 (nth (atoi (get_tile "txt-01")) list-01)
			str-02 (nth (atoi (get_tile "txt-02")) list-02)
);setq

(if (/= list-901 nil) 
	(setq list-901 (reverse list-901)
				list-902 (reverse list-902)
	);setq
);if

;;;;;;;///////////////////////////////////////////////////////////////
(if (= "Вентилятор" str-01)		
	(setq str-03 (nth (atoi (get_tile "txt-03")) list-03)
				str-04 (nth (atoi (get_tile "txt-04")) list-04)
				str-05 (nth (atoi (get_tile "txt-05")) list-05)
				str-99 (nth (atoi (get_tile "txt-06")) list-06)
				
				list-901 (vl-list* (strcat str-01 "  " str-02 "  Uпит. " str-03 "  Расход воздуха " str-04 "м3/ч  Размеры " str-05 " (ВхШ, мм)") list-901)
				
				tmp-902 (list (cons 1 str-01) (cons 2 str-02) (cons 3 (strcat "Uпит. " str-03)) (cons 4 (strcat "расход воздуха " str-04 " м3/ч"))
											(cons 5 (strcat "размеры " str-05 " (ВхШ, мм)")) (cons 98 "шт.") (cons 99 str-99));list
	);setq
);if


;;;;;;;///////////////////////////////////////////////////////////////
(if (= "Решетка с фильтром" str-01)
	(setq str-03 (nth (atoi (get_tile "txt-03")) list-03)
				str-99 (nth (atoi (get_tile "txt-04")) list-04)
				
				list-901 (vl-list* (strcat str-01 "  " str-02 "  Размеры " str-03 " (ВхШ, мм)") list-901)
				
				tmp-902 (list (cons 1 str-01) (cons 2 str-02) (cons 3 (strcat "размеры " str-03 " (ВхШ, мм)"))
											(cons 98 "компл.") (cons 99 str-99));list
	);setq
);if

;;;;;;;///////////////////////////////////////////////////////////////
(if (= "Фильтр сменный" str-01)
	(setq str-03 (nth (atoi (get_tile "txt-03")) list-03)
				str-99 (nth (atoi (get_tile "txt-04")) list-04)
				
				list-901 (vl-list* (strcat str-01 "  " str-02 "  Размеры " str-03 " (ВхШ, мм)") list-901)
				
				tmp-902 (list (cons 1 str-01) (cons 2 str-02) (cons 3 (strcat "размеры " str-03 " (ВхШ, мм)"))
											(cons 98 "шт.") (cons 99 str-99));list
	);setq
);if

;;;;;;;///////////////////////////////////////////////////////////////
(if (= "Термостат" str-01)		
	(setq str-03 (nth (atoi (get_tile "txt-03")) list-03)
				str-04 (nth (atoi (get_tile "txt-04")) list-04)
				str-99 (nth (atoi (get_tile "txt-05")) list-05)
				
				list-901 (vl-list* (strcat str-01 "  " str-02 "  Температура " str-03 "°С  Тип контакта " str-04) list-901)
				
				tmp-902 (list (cons 1 str-01) (cons 2 str-02) (cons 3 (strcat "диапазон регулир. " str-03 "%%dC")) (cons 4 (strcat "тип контакта " str-04))
											(cons 98 "шт.") (cons 99 str-99));list
	);setq
);if


(setq list-901 (reverse list-901)
			list-902 (vl-list* tmp-902 list-902)
			list-902 (reverse list-902)
);setq

(list-filling "txt-901" list-901)

(princ)
)
;;;;///////////////////////////////////////////////////////////////////////////////////////////////////////////////
;;;;///////////////////////////////////////////////////////////////////////////////////////////////////////////////


;;;;///////////////////////////////////////////////////////////////////////////////////////////////////////////////
;;;;подпрограмма вывода в ПЭ                   ////////////////////////////////////////////////////////////////////
(defun le-101-04-microclim-dkc-01-general

(list-902 / cntr-1 pnt-ins str-01 str-02 str-03 str-04 str-05 str-701 str-702 str-tmp)

(setq cntr-1 0
			str-702 nil
);setq

(repeat (length list-902)
	(setq str-tmp (nth cntr-1 list-902)
				str-01 (cdr (assoc 1 str-tmp))	
				str-02 (cdr (assoc 2 str-tmp))			
				str-03 (cdr (assoc 3 str-tmp))
	);setq
	
	(setvar "osmode" 6199)
	
	(setq pnt-ins (getpoint "\nУкажите точку вставки\n"));setq
	
	;;;;;;;/////////////////////////////////////////////////////////////
	(if (= "Вентилятор" str-01)
		(setq str-04 (cdr (assoc 4 str-tmp))
					str-05 (cdr (assoc 5 str-tmp))
										
					str-701 (strcat str-01 " ДКС, артикул " str-02 ", " str-03 ", " str-04 ", " str-05)	
		);setq
	);if

	;;;;;;;/////////////////////////////////////////////////////////////
	(if (or (= "Решетка с фильтром" str-01)
					(= "Фильтр сменный" str-01));or
		(setq str-701 (strcat str-01 " ДКС, артикул " str-02 ", " str-03));setq
	);if

	;;;;;;;/////////////////////////////////////////////////////////////
	(if (= "Термостат" str-01)
		(setq str-04 (cdr (assoc 4 str-tmp))
					
					str-701 (strcat str-01 " ДКС, артикул " str-02 ", " str-03 ", " str-04)	
		);setq
	);if

	(split-str-parts-le-01-general str-701 str-702 pnt-ins "**1**");

	(setq cntr-1 (1+ cntr-1));setq
);repeat

(princ)
)
;;;;///////////////////////////////////////////////////////////////////////////////////////////////////////////////
;;;;///////////////////////////////////////////////////////////////////////////////////////////////////////////////


;;;;///////////////////////////////////////////////////////////////////////////////////////////////////////////////
;;;;подпрограмма вывода в спцф                   //////////////////////////////////////////////////////////////////
(defun spcf-101-04-microclim-dkc-01-general

(list-902 / cntr-1 pnt-ins str-01 str-01-mdf str-02 str-03 str-04 str-701 str-702 str-99 str-crtf str-manufact str-order str-tmp str-unit)

(setq cntr-1 0);setq

(repeat (length list-902)
	(setq str-tmp (nth cntr-1 list-902)
				str-01 (cdr (assoc 1 str-tmp))
				str-98 (cdr (assoc 98 str-tmp))
				str-99 (cdr (assoc 99 str-tmp))
	);setq
	
	(setvar "osmode" 6199)
	
	(setq pnt-ins (getpoint "\nУкажите точку вставки\n"));setq
	
	;;;;;;;/////////////////////////////////////////////////////////////
	(if (wcmatch str-01 "S 200,*")
		(setq str-701 "Выключатель автоматический"
				
					str-01-mdf (vl-string-left-trim "S 200, " str-01)
				
					str-702 (list (cons 1 str-01-mdf)
												(cons 2 (strcat "Iном. " str-02 "А")));list
											 
					str-order (list (cons 1 (strcat str-03 ", код заказа " str-04)) 
													(cons 2 ",") 
													(cons 3 nil));list
		);setq
	);if
	
	
	

	(setq str-manufact "ABB"
				str-unit "шт."
				str-crtf nil
	);setq
	
	(split-str-parts-spcf-01-general str-701 str-702 str-order str-manufact str-unit str-99 str-crtf pnt-ins) 
 
	(setq cntr-1 (+ cntr-1 1));setq
);repeat

(princ)
)
;;;;///////////////////////////////////////////////////////////////////////////////////////////////////////////////
;;;;///////////////////////////////////////////////////////////////////////////////////////////////////////////////


;;;;///////////////////////////////////////////////////////////////////////////////////////////////////////////////
;;;;подпрограмма вывода в овш               ///////////////////////////////////////////////////////////////////////
(defun lecgv-101-04-microclim-dkc-01-general

(list-902 / cntr-1 pnt-ins str-01 str-02 str-03 str-04 str-05 str-701 str-702 str-703 str-99 str-tmp)

(setq cntr-1 0
			str-702 nil
			str-703 nil
);setq

(repeat (length list-902)
	(setq str-tmp (nth cntr-1 list-902)
				str-01 (cdr (assoc 1 str-tmp))
				str-02 (cdr (assoc 2 str-tmp))
				str-03 (cdr (assoc 3 str-tmp))
				str-99 (cdr (assoc 99 str-tmp))
	);setq
	
;(princ "\n         str-tmp = ") (princ str-tmp);Erase_DV
;(getstring "\nPress Enter to continue...");Erase_DV
	
	(setvar "osmode" 6199)
	
	(setq pnt-ins (getpoint "\nУкажите точку вставки\n"));setq
	
	;;;;;;;/////////////////////////////////////////////////////////////
	(if (= "Вентилятор" str-01)
		(setq str-04 (cdr (assoc 4 str-tmp))
					str-05 (cdr (assoc 5 str-tmp))
										
					str-701 (strcat str-01 " ДКС, артикул " str-02 ", " str-03 ", " str-04 ", " str-05)	
		);setq
	);if

	;;;;;;;/////////////////////////////////////////////////////////////
	(if (or (= "Решетка с фильтром" str-01)
					(= "Фильтр сменный" str-01));or
		(setq str-701 (strcat str-01 ", артикул " str-02 ", " str-03));setq
	);if

	;;;;;;;/////////////////////////////////////////////////////////////
	(if (= "Термостат" str-01)
		(setq str-04 (cdr (assoc 4 str-tmp))
					
					str-701 (strcat str-01 " ДКС, артикул " str-02 ", " str-03 ", " str-04)	
		);setq
	);if
	
	
	
	

	(split-str-parts-lecgv-01-general str-701 str-702 str-703 str-99 pnt-ins);

	(setq cntr-1 (+ cntr-1 1));setq
);repeat

(princ)
)

;;;;///////////////////////////////////////////////////////////////////////////////////////////////////////////////
;;;;///////////////////////////////////////////////////////////////////////////////////////////////////////////////
