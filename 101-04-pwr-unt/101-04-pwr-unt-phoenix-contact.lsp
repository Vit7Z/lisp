;/////// ************************************************************ //////////////////////////////////////////////////////////////////
;///////                                                                   /////////////////////////////////////////////////////////////
;/////// ************************************************************ //////////////////////////////////////////////////////////////////
(defun 101-04-pwr-unt-phoenix-contact

( / adoc dcl-id list-01 list-02 list-03 list-04 list-05 list-06 list-07 list-08 list-901 list-902 str-01 type-list)

(vl-load-com)

(vla-startundomark (setq adoc (vla-get-activedocument (vlax-get-acad-object))));start undo

(setq str-01 nil
      list-01 (list "QUINT POWER" "QUINT DIODE")
      list-901 nil
      list-902 nil
);setq

(start-101-04-pwr-unt-phoenix-contact)

(if (< (setq dcl-id (load_dialog "dia-101-04-pwr-unt-phoenix-contact.dcl")) 0) ;ищем диалог
		(progn
			(alert "Не найден dcl-файл")
			(exit)
		);progn
);if

(if (not (new_dialog "dia_101_04_pwr_unt_phoenix_contact" dcl-id))
		(exit)
);if

(list-filling "txt-01" list-01)
(list-filling "txt-02" list-02)
(list-filling "txt-03" list-03)
(list-filling "txt-04" list-04)
(list-filling "txt-05" list-05)
(list-filling "txt-06" list-06)
(list-filling "txt-07" list-07)
(list-filling "txt-08" list-08)

(set_tile "txt-01" "0")
(set_tile "txt-02" "0")
(set_tile "txt-03" "0")
(set_tile "txt-04" "0")
(set_tile "txt-05" "0")
(set_tile "txt-06" "0")
(set_tile "txt-07" "0")
(set_tile "txt-08" "0")

(action_tile "txt-01"
  (strcat "(start-101-04-pwr-unt-phoenix-contact)");srcat
);action_tile

(action_tile "txt-02"
  (strcat "(txt-02-101-04-pwr-unt-phoenix-contact)");srcat
);action_tile

(action_tile "txt-03"
  (strcat "(txt-03-101-04-pwr-unt-phoenix-contact)");srcat
);action_tile

(action_tile "txt-04"
  (strcat "(txt-04-101-04-pwr-unt-phoenix-contact)");srcat
);action_tile

(action_tile "txt-05"
  (strcat "(txt-05-101-04-pwr-unt-phoenix-contact)");srcat
);action_tile

(action_tile "txt-06"
  (strcat "(txt-06-101-04-pwr-unt-phoenix-contact)");srcat
);action_tile

(action_tile "but1"
  (strcat "(but1-101-04-pwr-unt-phoenix-contact)"
  				"(list-filling \"txt-01\" list-01)"
  				"(list-filling \"txt-02\" list-02)"
					"(list-filling \"txt-03\" list-03)"
					"(list-filling \"txt-04\" list-04)"
					"(list-filling \"txt-05\" list-05)"
					"(set_tile \"txt-01\" \"0\")"
					"(set_tile \"txt-02\" \"0\")"
          "(set_tile \"txt-03\" \"0\")"
          "(set_tile \"txt-04\" \"0\")"
          "(set_tile \"txt-05\" \"0\")"
          "(set_tile \"txt-06\" \"0\")"
  );strcat
);action_tile

(action_tile "but2"
  (strcat "(setq type-list \"le\")"
          "(done_dialog)"
  );strcat
);action_tile

(action_tile "but3"
  (strcat "(setq type-list \"spcf\")"
          "(done_dialog)"
  );strcat
);action_tile

(action_tile "but4"
  (strcat "(setq type-list \"lecgv\")"
          "(done_dialog)"
  );strcat
);action_tile

(action_tile "accept"
  (strcat "(done_dialog)"
          "(exit)"
  );strcat
);action_tile

(start_dialog)
(unload_dialog dcl-id)

(if (= type-list "le") (le-101-04-pwr-unt-phoenix-contact));if

(if (= type-list "spcf") (spcf-101-04-pwr-unt-phoenix-contact));if

(if (= type-list "lecgv") (lecgv-101-04-pwr-unt-phoenix-contact));if

(setvar "osmode" 6199)
(setvar "cmdecho" 1)
(vla-endundomark adoc)
(gc)
(princ)
)
;/////// конец программы ////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun start-101-04-pwr-unt-phoenix-contact

( / list-01-read-file list-02-read-file list-03-read-file list-04-read-file list-05-read-file list-06-read-file list-07-read-file)

(if (= nil str-01) 
	(setq str-01 (nth 0 list-01));setq
	(setq str-01 (nth (atoi (get_tile "txt-01")) list-01));setq
);if

(cond
	((= str-01 "QUINT POWER")
		(set_tile "ptxt-031" "Uвыход,")
		(set_tile "ptxt-032" "В")
		(set_tile "ptxt-041" "Iнагр,")
		(set_tile "ptxt-042" "А")
		(set_tile "ptxt-071" "Развязка")
		(set_tile "ptxt-072" "каналов")
	);=

	((= str-01 "QUINT DIODE")
		(set_tile "ptxt-031" "Iвход,")
		(set_tile "ptxt-032" "A")
		(set_tile "ptxt-041" "Iвыход,")
		(set_tile "ptxt-042" "А")
		(set_tile "ptxt-071" "")
		(set_tile "ptxt-072" "")
	);=
);cond


(cond
	((= str-01 "QUINT POWER")
		(read-file-for-dialog-box "101-04-pwr-unt-phoenix-contact-quint-power.txt" 7)
	);=

	((= str-01 "QUINT DIODE")
		(progn
			(read-file-for-dialog-box "101-04-pwr-unt-phoenix-contact-quint-diode.txt" 6)
			(setq list-07-read-file list-06-read-file
						list-06-read-file nil
			);setq
		);progn
	);=
);cond

(setq list-02 list-01-read-file
			list-03 list-02-read-file
			list-04 list-03-read-file
			list-05 list-04-read-file
			list-06 list-05-read-file
			list-07 list-06-read-file
			list-08 list-07-read-file
);setq

(list-filling "txt-02" list-02)
(list-filling "txt-03" list-03)
(list-filling "txt-04" list-04)
(list-filling "txt-05" list-05)
(list-filling "txt-06" list-06)
(list-filling "txt-07" list-07)
(list-filling "txt-08" list-08)

(set_tile "txt-02" "0")
(set_tile "txt-03" "0")
(set_tile "txt-04" "0")
(set_tile "txt-05" "0")
(set_tile "txt-06" "0")
(set_tile "txt-07" "0")
(set_tile "txt-08" "0")





(princ)
)
;;;;/////////////////////////////////////////////////////////////////////////////////////////////////////////////////////////////////////////////////////////////////////////////
;;;;/////////////////////////////////////////////////////////////////////////////////////////////////////////////////////////////////////////////////////////////////////////////


;;;;/////////////////////////////////////////////////////////////////////////////////////////////////////////////////////////////////////////////////////////////////////////////
;;;;подпрограмма для txt-02//////////////////////////////////////////////////////////////////////////////////////////////////////////////////////////////////////////////////////
(defun txt-02-101-04-pwr-unt-phoenix-contact

( / str-01)

(setq str-01 (get_tile "txt-02"));setq

(set_tile "txt-03" str-01)
(set_tile "txt-04" str-01)
(set_tile "txt-05" str-01)
(set_tile "txt-06" str-01)
(set_tile "txt-07" str-01)
(set_tile "txt-08" str-01)

(princ)
)
;;;;////////////////////////////////////////////////////////////////////////////////////////////////////////////////////////////////////////////////////////////////////////////
;;;;////////////////////////////////////////////////////////////////////////////////////////////////////////////////////////////////////////////////////////////////////////////

;;;;////////////////////////////////////////////////////////////////////////////////////////////////////////////////////////////////////////////////////////////////////////////
;;;;подпрограмма для txt-03/////////////////////////////////////////////////////////////////////////////////////////////////////////////////////////////////////////////////////
(defun txt-03-101-04-pwr-unt-phoenix-contact

( / str-01)

(setq str-01 (get_tile "txt-03"));setq

(set_tile "txt-02" str-01)
(set_tile "txt-04" str-01)
(set_tile "txt-05" str-01)
(set_tile "txt-06" str-01)
(set_tile "txt-07" str-01)
(set_tile "txt-08" str-01)

(princ)
)
;;;;///////////////////////////////////////////////////////////////////////////////////////////////////////////////////////////////////////////////////////////////////////////
;;;;///////////////////////////////////////////////////////////////////////////////////////////////////////////////////////////////////////////////////////////////////////////


;;;;///////////////////////////////////////////////////////////////////////////////////////////////////////////////////////////////////////////////////////////////////////////
;;;;подпрограмма для txt-04////////////////////////////////////////////////////////////////////////////////////////////////////////////////////////////////////////////////////
(defun txt-04-101-04-pwr-unt-phoenix-contact

( / str-01)

(setq str-01 (get_tile "txt-04"));setq

(set_tile "txt-02" str-01)
(set_tile "txt-03" str-01)
(set_tile "txt-05" str-01)
(set_tile "txt-06" str-01)
(set_tile "txt-07" str-01)
(set_tile "txt-08" str-01)

(princ)
)
;;;;//////////////////////////////////////////////////////////////////////////////////////////////////////////////////////////////////////////////////////////////////////////////////////////////////////////
;;;;//////////////////////////////////////////////////////////////////////////////////////////////////////////////////////////////////////////////////////////////////////////////////////////////////////////

;;;;///////////////////////////////////////////////////////////////////////////////////////////////////////////////////////////////////////////////////////////////////////////////////////////////////////////
;;;;подпрограмма для txt-05////////////////////////////////////////////////////////////////////////////////////////////////////////////////////////////////////////////////////////////////////////////////////
(defun txt-05-101-04-pwr-unt-phoenix-contact

( / str-01)

(setq str-01 (get_tile "txt-05"));setq

(set_tile "txt-02" str-01)
(set_tile "txt-03" str-01)
(set_tile "txt-04" str-01)
(set_tile "txt-06" str-01)
(set_tile "txt-07" str-01)
(set_tile "txt-08" str-01)

(princ)
)
;;;;//////////////////////////////////////////////////////////////////////////////////////////////////////////////////////////////////////////////////////////////////////////////////////////////////////////
;;;;//////////////////////////////////////////////////////////////////////////////////////////////////////////////////////////////////////////////////////////////////////////////////////////////////////////

;;;;///////////////////////////////////////////////////////////////////////////////////////////////////////////////////////////////////////////////////////////////////////////////////////////////////////////
;;;;подпрограмма для txt-06////////////////////////////////////////////////////////////////////////////////////////////////////////////////////////////////////////////////////////////////////////////////////
(defun txt-06-101-04-pwr-unt-phoenix-contact

( / str-01)

(setq str-01 (get_tile "txt-06"));setq

(set_tile "txt-02" str-01)
(set_tile "txt-03" str-01)
(set_tile "txt-04" str-01)
(set_tile "txt-05" str-01)
(set_tile "txt-07" str-01)
(set_tile "txt-08" str-01)

(princ)
)
;;;;//////////////////////////////////////////////////////////////////////////////////////////////////////////////////////////////////////////////////////////////////////////////////////////////////////////
;;;;//////////////////////////////////////////////////////////////////////////////////////////////////////////////////////////////////////////////////////////////////////////////////////////////////////////

;;;;///////////////////////////////////////////////////////////////////////////////////////////////////////////////////////////////////////////////////////////////////////////////////////////////////////////
;;;;подпрограмма формирования данных///////////////////////////////////////////////////////////////////////////////////////////////////////////////////////////////////////////////////////////////////////////
(defun but1-101-04-pwr-unt-phoenix-contact

( / str-01 str-02 str-03 str-04 str-05 str-06 str-99 swtch tmp-list-902)

(setq str-01 (nth (atoi (get_tile "txt-01")) list-01)
			str-02 (nth (atoi (get_tile "txt-02")) list-02)
			str-03 (nth (atoi (get_tile "txt-03")) list-03)
			str-04 (nth (atoi (get_tile "txt-04")) list-04)
			str-05 (nth (atoi (get_tile "txt-05")) list-05)
			str-06 (nth (atoi (get_tile "txt-06")) list-06)
			str-99 (nth (atoi (get_tile "txt-08")) list-08)
);setq

(if (/= list-901 nil) (setq list-902 (reverse list-902)));if

;;;;;;;/////////////////////////////////////////////////////////////////////////////////////////////
(if (= str-01 "QUINT POWER")
	(progn		
		(setq list-901 (vl-list* (strcat str-01 "  Uвход " 
																		 str-02 "В  Iнагр " 
																		 str-04 "А  "
																		 str-05 "  Артикул "
																		 str-06) list-901)
  	
					tmp-list-902 (list (cons 1 str-01) (cons 2 str-02) (cons 3 str-03) (cons 4 str-04) (cons 5 str-05) (cons 6 str-06) (cons 99 str-99))
					
		);setq
	);progn	
);if

;;;;;;;/////////////////////////////////////////////////////////////////////////////////////////////
(if (= str-01 "QUINT DIODE")
	(progn		
		(setq list-901 (vl-list* (strcat str-01 "  Uвход " 
																		 str-02 "В  Iвход " 
																		 str-03 "А  Iвыход "
																		 str-04 "A  Артикул "
																		 str-06) list-901)
  	
				tmp-list-902 (list (cons 1 str-01) (cons 2 str-02) (cons 3 str-03) (cons 4 str-04) (cons 5 str-05) (cons 6 str-06) (cons 99 str-99))
		);setq
	);progn	
);if

(setq list-902 (vl-list* tmp-list-902 list-902)
			list-902 (reverse list-902)
);setq

(list-filling "txt-901" (reverse list-901))

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;подпрограмма вывода в ПЭ                   //////////////////////////////////////////////////////////////////////////////////////////////////////////////////////////////////
(defun le-101-04-pwr-unt-phoenix-contact

( / cntr-1 pnt-ins str-01 str-02 str-03 str-04 str-05 str-06 str-701 str-702 str-tmp)

(setq cntr-1 0);setq

(repeat (length list-902)
	(setq str-tmp (nth cntr-1 list-902)
				str-01 (cdr (assoc 1 str-tmp))
				str-02 (cdr (assoc 2 str-tmp))
				str-03 (cdr (assoc 3 str-tmp))
				str-04 (cdr (assoc 4 str-tmp))
				str-05 (cdr (assoc 5 str-tmp))
				str-06 (cdr (assoc 6 str-tmp))
	);setq
	
	(setvar "osmode" 6199)
	
	(setq pnt-ins (getpoint "\nУкажите точку вставки\n"));setq
	
	;;;;////////////////////////////////////////////////////////////////////////
	(if (= str-01 "QUINT POWER")
		(setq str-701 (strcat "Блок питания Phoenix Contact, " str-05 ", артикул " str-06 ", Uвход " str-02 "В, Uвыход " str-03 "В, Iнагр " str-04 "А")
					str-702 nil
		);setq
	);if

	;;;;////////////////////////////////////////////////////////////////////////
	(if (= str-01 "QUINT DIODE")
		(setq str-701 (strcat "Диодный модуль Phoenix Contact, " str-05 ", артикул " str-06 ", Uвход "str-02 "В, Iвход " str-03 "А, Iвыход " str-04 "А")
					str-702 nil
		);setq
	);if
	
	(split-str-parts-le-01-general str-701 str-702 pnt-ins);
	
	(setq cntr-1 (1+ cntr-1));счетчик
);repeat

(princ)
)
;;;;///////////////////////////////////////////////////////////////////////////////////////////////////////////////////////////////////////////////////////////////////////////////////////////////////////////
;;;;///////////////////////////////////////////////////////////////////////////////////////////////////////////////////////////////////////////////////////////////////////////////////////////////////////////

;;;;///////////////////////////////////////////////////////////////////////////////////////////////////////////////////////////////////////////////////////////////////////////////////////////////////////////
;;;;подпрограмма вывода в спцф                   //////////////////////////////////////////////////////////////////////////////////////////////////////////////////////////////////////////////////////////////
(defun spcf-101-04-pwr-unt-phoenix-contact

( / cntr-1 pnt-ins str-01 str-02 str-03 str-04 str-05 str-06 str-701 str-702 str-99 str-crtf str-manufact str-order str-tmp str-unit)

(setq cntr-1 0);setq

(repeat (length list-902)
	(setq str-tmp (nth cntr-1 list-902)
				str-01 (cdr (assoc 1 str-tmp))
				str-02 (cdr (assoc 2 str-tmp))
				str-03 (cdr (assoc 3 str-tmp))
				str-04 (cdr (assoc 4 str-tmp))
				str-05 (cdr (assoc 5 str-tmp))
				str-06 (cdr (assoc 6 str-tmp))
				str-99 (cdr (assoc 99 str-tmp))
	);setq
	
	(setvar "osmode" 6199)
	
	(setq pnt-ins (getpoint "\nУкажите точку вставки\n"));setq

	;/////////////////////////////////////////////////////////////////////////////////////////////////
	(if (= "QUINT POWER" str-01)
		(setq str-701 "Блок питания"
			
					str-702 (list (cons 1 (strcat "Uвход " str-02 "В, Uвыход " str-03 "В, Iнагр " str-04 "А")));list
															
					str-order (list (cons 1 (strcat str-05 ", артикул " str-06)) 
													(cons 2 ",") 
													(cons 3 nil));list
						
					str-unit "шт"
			);setq
	);if

	;/////////////////////////////////////////////////////////////////////////////////////////////////
	(if (= "QUINT DIODE" str-01)
		(setq str-701 "Диодный модуль"
			
					str-702 (list (cons 1 (strcat "Uвход "str-02 "В, Iвход " str-03 "А, Iвыход " str-04 "А")));list
															
					str-order (list (cons 1 (strcat str-05 ", артикул " str-06)) 
													(cons 2 "/") 
													(cons 3 nil));list
						
					str-unit "шт"
			);setq
	);if

	(setq str-manufact "Phoenix Contact"
				str-crtf nil
	);setq
			
	(split-str-parts-spcf-01-general str-701 str-702 str-order str-manufact str-unit str-99 str-crtf pnt-ins)

	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////

;;;;////////////////////////////////////////////////////////////////////////////////////////////////////////////////////////////////////////////////////////////////////////////
;;;;подпрограмма вывода в овш               ////////////////////////////////////////////////////////////////////////////////////////////////////////////////////////////////////
(defun lecgv-101-04-pwr-unt-phoenix-contact

( / cntr-1 pnt-ins str-01 str-02 str-03 str-04 str-05 str-06 str-701 str-702 str-703 str-99 str-tmp)

(setq cntr-1 0);setq

(repeat (length list-902)
	(setq str-tmp (nth cntr-1 list-902)
				str-01 (cdr (assoc 1 str-tmp))
				str-02 (cdr (assoc 2 str-tmp))
				str-03 (cdr (assoc 3 str-tmp))
				str-04 (cdr (assoc 4 str-tmp))
				str-05 (cdr (assoc 5 str-tmp))
				str-06 (cdr (assoc 6 str-tmp))
				str-99 (cdr (assoc 99 str-tmp))
	);setq
	
	(setvar "osmode" 6199)
	
	(setq pnt-ins		(getpoint "\nУкажите точку вставки\n"));setq

	;;;;////////////////////////////////////////////////////////////////////////
	(if (= str-01 "QUINT POWER")
		(setq str-701 (strcat "Блок питания Phoenix Contact, " str-05 ", артикул " str-06 ", Uвход " str-02 "В, Uвыход " str-03 "В, Iнагр " str-04 "А")
					str-702 nil
					str-703 nil
		);setq
	);if

	;;;;////////////////////////////////////////////////////////////////////////
	(if (= str-01 "QUINT DIODE")
		(setq str-701 (strcat "Диодный модуль Phoenix Contact, " str-05 ", артикул " str-06 ", Uвход " str-02 "В, Iвход " str-03 "В, Iвыход " str-04 "А")
					str-702 nil
					str-703 nil
		);setq
	);if
	
	(split-str-parts-lecgv-01-general str-701 str-702 str-703 str-99 pnt-ins);
	
	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////
