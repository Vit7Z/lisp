;/////// ************************************************************ //////////////////////////////////////////////////////////////////
;///////                                                              //////////////////////////////////////////////////////////////////
;/////// ************************************************************ //////////////////////////////////////////////////////////////////
(defun c:101-eja110a-etalon

( / adoc dcl-id list-10 list-15 list-16 list-17 list-18 list-20 list-21 list-211 list-22 list-221 list-23 list-24 list-31 list-32 
list-33 list-34 num-lin pnt-ins txt-10 txt-11 txt-12 txt-121 txt-13 txt-14 txt-15 txt-15-1 txt-15-2 txt-16 txt-16-1 txt-17 txt-17-1 
txt-17-2 txt-17-3 txt-18 txt-18-1 txt-18-2 txt-20 txt-20-1 txt-20-2 txt-20-3 txt-21 txt-211 txt-21-1 txt-211-1 txt-211-2 txt-21-2 
txt-21-3 txt-22 txt-221 txt-22-1 txt-221-1 txt-221-2 txt-22-2 txt-22-3 txt-23 txt-23-1 txt-23-2 txt-24 txt-24-1 txt-24-2 txt-31 
txt-31-1 txt-31-2 txt-ins-1 txt-ins-2 x-pnt-ins y-pnt-ins ypnt-ins-1)

(vl-load-com)
(vla-startundomark
  (setq adoc (vla-get-activedocument (vlax-get-acad-object))
  );setq
);start undo

(setq num-lin 24
      list-10 (list "Вода" "Насыщенный пар" "Перегретый пар" "Газ природный" "Нефть" "Кислород" "Мазут")
      list-15 (list "4...20мА, HART" "4...20мА, BRAIN" "FOUNDATION Fieldbus")
      list-16 (list "Нет" "Корнеизвлечение" "Инверсный")      
      list-17 (list "-10...10 кПа (0,5...10)" "-100...100 кПа (1...100)" "-500...500 кПа (5...500)" "-0,5...14 МПа (0,14...14)")
      list-20 (list "SCS14A (фланцы), SUS316L (капусла), SUS316 (клапаны)"
                    "SCS14A (фланцы), Hastelloy C-276 (капусла), SUS316 (клапаны)"
                    "SCS14A (фланцы), Monel (капусла), SUS316 (клапаны)"
                    "SCS14A (фланцы), Tantalum (капусла), SUS316 (клапаны)"
                    "Hastelloy C-276 (фланцы), Hastelloy C-276 (капусла), Hastelloy C-276 (клапаны)"
                    "Hastelloy C-276 (фланцы), Tantalum (капусла), Hastelloy C-276 (клапаны)"
                    "Monel (фланцы), Monel (капусла), Monel (клапаны)"
                    )
      list-21 (list "С фланц., резьба внутр. R1/2 (BSPT) ГОСТ 6211-81"
                    "Без фланц., резьба внутр. R1/4 (BSPT) ГОСТ 6211-81"
                    "Без фланц., резьба внутр. K1/4 (NPT) ГОСТ 6111-52"
                    "С фланц., резьба внутр. R1/4 (BSPT) ГОСТ 6211-81"
                    "С фланц., резьба внутр. K1/4 (NPT) ГОСТ 6111-52"
                    "С фланц., резьба внутр. K1/2 (NPT) ГОСТ 6111-52"
                    )
      list-211 (list "Углеродистая сталь SCM435"
                     "Нержавеющая сталь SUS630"
                     "Нержавеющая сталь SUH660"
                    )
      list-22 (list "Подвод имп. труб вертик., высок. давл. справа, присоединен. сверху"
                    "Подвод имп. труб вертик., высок. давл. справа, присоединен. снизу"
                    "Подвод имп. труб вертик., высок. давл. слева, присоединен. сверху"
                    "Подвод имп. труб вертик., высок. давл. слева, присоединен. снизу"
                    "Подвод имп. труб гориз., высок. давл. справа, присоединен. гориз."
                    "Подвод имп. труб гориз., высок. давл. слева, присоединен. гориз."
                    )
      list-221 (list "М20х1,5" 
                     "G1/2 (BSP) ГОСТ 6357-81"
                     "К1/2 (NPT) ГОСТ 6111-52"
                     "Pg 13,5")
      list-23 (list "ЖК дисплей" "ЖК дисплей, переключ. шкалы" "Отсутствует")
      list-31 (list "Прямой, углеродистая сталь" "Нет" "Прямой, нержавеющая сталь" "Г-образный, углеродистая сталь" "Г-образный, нержавеющая сталь")
      list-18 (list "Стандартная")
      list-24 (list "Обычное, IP67" "0ExiaIICT5X" "1ExdIICT4...T6")
      list-32 (list "Нет"
                    "Обезжиривание контактирующих частей"
                    "Обезжиривание контактирующих частей, гидрозаполнение фторированным маслом")
      list-33 (list "Нет" "Бар" "Кгс/см2")      
      list-34 (list "Нет" "Нержавеющая сталь SCS14A")
      list-41 (list "3 вентиля, ниппеля под приварку" "5 вентилей, дренажные клапана, ниппеля под приварку" "Нет")
);setq

(if (< (setq dcl-id (load_dialog "101-dia-eja110a-etalon.dcl")) 0) ;ищем диалог
		(progn
			(alert "Не найден dcl-файл")
			(exit)
		);progn
);if

(if (not (new_dialog "dia_eja_110_etalon" dcl-id))
		(exit)
);if

(list-filling "txt-10" list-10)
(set_tile "txt-10" "0")

(list-filling "txt-15" list-15)
(set_tile "txt-15" "0")
 
(list-filling "txt-16" list-16)
(set_tile "txt-16" "0")

(list-filling "txt-17" list-17)
(set_tile "txt-17" "0")

(list-filling "txt-18" list-18)
(set_tile "txt-18" "0")

(list-filling "txt-20" list-20)
(set_tile "txt-20" "0")

(list-filling "txt-21" list-21)
(set_tile "txt-21" "0")

(list-filling "txt-211" list-211)
(set_tile "txt-211" "0")

(list-filling "txt-22" list-22)
(set_tile "txt-22" "0")

(list-filling "txt-221" list-221)
(set_tile "txt-221" "0")

(list-filling "txt-23" list-23)
(set_tile "txt-23" "0")

(list-filling "txt-24" list-24)
(set_tile "txt-24" "0")

(list-filling "txt-31" list-31)
(set_tile "txt-31" "0")

(list-filling "txt-32" list-32)
(list-filling "txt-33" list-33)
(list-filling "txt-34" list-34)
(list-filling "txt-41" list-41)
(set_tile "txt-41" "0")

(action_tile "txt-15" ;выбор выходного сигнала
  (strcat "(tmp-1-101-eja110a-etalon $value)"
  );strcat
);action_tile

(action_tile "txt-17" ;выбор выходного сигнала
  (strcat "(tmp-2-101-eja110a-etalon $value)"
  );strcat
);action_tile

(action_tile "txt-20" ;выбор выходного сигнала
  (strcat "(tmp-3-101-eja110a-etalon $value)"
  );strcat
);action_tile

(action_tile "accept"
  (strcat "(setq txt-10 (nth (atoi (get_tile \"txt-10\")) list-10))"
          "(setq txt-11 (get_tile \"txt-11\"))"
          "(setq txt-12 (get_tile \"txt-12\"))"
          "(setq txt-121 (get_tile \"txt-121\"))"
          "(setq txt-13 (get_tile \"txt-13\"))"
          "(setq txt-14 (get_tile \"txt-14\"))"
          "(setq txt-15 (nth (atoi (get_tile \"txt-15\")) list-15))"
          "(setq txt-16 (nth (atoi (get_tile \"txt-16\")) list-16))"
          "(setq txt-17 (nth (atoi (get_tile \"txt-17\")) list-17))"
          "(setq txt-18 (nth (atoi (get_tile \"txt-18\")) list-18))"
          "(setq txt-20 (nth (atoi (get_tile \"txt-20\")) list-20))"
          "(setq txt-21 (nth (atoi (get_tile \"txt-21\")) list-21))"
          "(setq txt-211 (nth (atoi (get_tile \"txt-211\")) list-211))"
          "(setq txt-22 (nth (atoi (get_tile \"txt-22\")) list-22))"
          "(setq txt-221 (nth (atoi (get_tile \"txt-221\")) list-221))"
          "(setq txt-23 (nth (atoi (get_tile \"txt-23\")) list-23))"
          "(setq txt-24 (nth (atoi (get_tile \"txt-24\")) list-24))"
          "(setq txt-31 (nth (atoi (get_tile \"txt-31\")) list-31))"
          "(setq txt-41 (nth (atoi (get_tile \"txt-41\")) list-41))"
          "(done_dialog)"
  );strcat
);action_tile

(action_tile "cancel"
  (strcat "(done_dialog)"
          "(exit)")
);action_tile

(start_dialog)
(unload_dialog dcl-id)

;//////////////////////////////////////////////////
(if (= txt-15 "4...20мА, HART")
  (setq txt-15-1 "-E"
        txt-15-2 "- выходной сигнал 4...20мА, HART"
  );setq
);if

(if (= txt-15 "4...20мА, BRAIN")
  (setq txt-15-1 "-D"
        txt-15-2 "- выходной сигнал 4...20мА, BRAIN"
  );setq
);if

(if (= txt-15 "FOUNDATION Fieldbus")
  (setq txt-15-1 "-F"
        txt-15-2 "- выходной сигнал FOUNDATION Fieldbus"
  );setq
);if

;//////////////////////////////////////////////////
(if (= txt-16 "Нет")  
  (setq txt-16-1 "- выходной сигнал без корнеизвлечения, без инверсии"
  );setq
);if

(if (= txt-16 "Корнеизвлечение")
  (setq txt-16-1 "- выходной сигнал с корнеизвлечением"
  );setq
);if

(if (= txt-16 "Инверсный")
  (setq txt-16-1 "- выходной сигнал инверсный"
  );setq
);if

;//////////////////////////////////////////////////
(if (= txt-17 "-10...10 кПа (0,5...10)")   
  (setq txt-17-1 "L"
        txt-17-2 "- пределы измерений датчика -10...10 кПа"
        txt-17-3 "- пределы перенастройки 0,5...10 кПа"
  );setq
);if

(if (= txt-17 "-100...100 кПа (1...100)")
  (setq txt-17-1 "M"
        txt-17-2 "- пределы измерений датчика -100...100 кПа"
        txt-17-3 "- пределы перенастройки 1...100 кПа"
  );setq
);if

(if (= txt-17 "-500...500 кПа (5...500)")
  (setq txt-17-1 "H"
        txt-17-2 "- пределы измерений датчика -500...500 кПа"
        txt-17-3 "- пределы перенастройки 5...500 кПа"
  );setq
);if

(if (= txt-17 "-0,5...14 МПа (0,14...14)")
  (setq txt-17-1 "V"
        txt-17-2 "- пределы измерений датчика -0,5...14 МПа"
        txt-17-3 "- пределы перенастройки 0,14...14 МПа"
  );setq
);if

;//////////////////////////////////////////////////
(if (= txt-20 "SCS14A (фланцы), SUS316L (капусла), SUS316 (клапаны)")  
  (setq txt-20-1 "S"
        txt-20-2 "- материал частей SCS14A (фланцы), SUS316L (капусла),"
        txt-20-3 "SUS316 (клапаны)"
  );setq
);if

(if (= txt-20 "SCS14A (фланцы), Hastelloy C-276 (капусла), SUS316 (клапаны)")
  (setq txt-20-1 "H"
        txt-20-2 "- материал частей SCS14A (фланцы), Hastelloy C-276 (капусла),"
        txt-20-3 "SUS316 (клапаны)"
  );setq
);if

(if (= txt-20 "SCS14A (фланцы), Monel (капусла), SUS316 (клапаны)")  
  (setq txt-20-1 "M"
        txt-20-2 "- материал частей SCS14A (фланцы), Monel (капусла),"
        txt-20-3 "SUS316 (клапаны)"
  );setq
);if

(if (= txt-20 "SCS14A (фланцы), Tantalum (капусла), SUS316 (клапаны)")
  (setq txt-20-1 "T"
        txt-20-2 "- материал частей SCS14A (фланцы), Tantalum (капусла), "
        txt-20-3 "SUS316 (клапаны)"
  );setq
);if

(if (= txt-20 "Hastelloy C-276 (фланцы), Hastelloy C-276 (капусла), Hastelloy C-276 (клапаны)")  
  (setq txt-20-1 "A"
        txt-20-2 "- материал частей Hastelloy C-276 (фланцы), Hastelloy C-276 (капусла), "
        txt-20-3 "Hastelloy C-276 (клапаны)"
  );setq
);if

(if (= txt-20 "Hastelloy C-276 (фланцы), Tantalum (капусла), Hastelloy C-276 (клапаны)")
  (setq txt-20-1 "D"
        txt-20-2 "- материал частей Hastelloy C-276 (фланцы), Tantalum (капусла), "
        txt-20-3 "Hastelloy C-276 (клапаны)"
  );setq
);if

(if (= txt-20 "Monel (фланцы), Monel (капусла), Monel (клапаны)")  
  (setq txt-20-1 "B"
        txt-20-2 "- материал частей Monel (фланцы), Monel (капусла), "
        txt-20-3 "Monel (клапаны)"
  );setq
);if
                
;//////////////////////////////////////////////////
(if (= txt-21 "Без фланц., резьба внутр. R1/4 (BSPT) ГОСТ 6211-81")
  (setq txt-21-1 "0"
        txt-21-2 "- присоединение к процессу без фланцев-переходников, "
        txt-21-3 "резьба внутр. R1/4 (BSPT) ГОСТ 6211-81"
  );setq
);if

(if (= txt-21 "Без фланц., резьба внутр. K1/4 (NPT) ГОСТ 6111-52")
  (setq txt-21-1 "5"
        txt-21-2 "- присоединение к процессу без фланцев-переходников, "
        txt-21-3 "резьба внутр. K1/4 (NPT) ГОСТ 6111-52"
  );setq
);if

(if (= txt-21 "С фланц., резьба внутр. R1/4 (BSPT) ГОСТ 6211-81")
  (setq txt-21-1 "1"
        txt-21-2 "- присоединение к процессу с фланцами-переходниками,"
        txt-21-3 "резьба внутр. R1/4 (BSPT) ГОСТ 6211-81"
  );setq
);if

(if (= txt-21 "С фланц., резьба внутр. R1/2 (BSPT) ГОСТ 6211-81")
  (setq txt-21-1 "2"
        txt-21-2 "- присоединение к процессу с фланцами-переходниками,"
        txt-21-3 "резьба внутр. R1/2 (BSPT) ГОСТ 6211-81"
  );setq
);if

(if (= txt-21 "С фланц., резьба внутр. K1/4 (NPT) ГОСТ 6111-52")
  (setq txt-21-1 "3"
        txt-21-2 "- присоединение к процессу с фланцами-переходниками,"
        txt-21-3 "резьба внутр. K1/4 (NPT) ГОСТ 6111-52"
  );setq
);if

(if (= txt-21 "С фланц., резьба внутр. K1/2 (NPT) ГОСТ 6111-52")
  (setq txt-21-1 "4"
        txt-21-2 "- присоединение к процессу с фланцами-переходниками,"
        txt-21-3 "резьба внутр. K1/2 (NPT) ГОСТ 6111-52"
  );setq
);if

;//////////////////////////////////////////////////
(if (= txt-211 "Углеродистая сталь SCM435")
  (setq txt-211-1 "A"
        txt-211-2 "- материал стяжных болтов (гаек) углеродистая сталь SCM435"
  );setq
);if

(if (= txt-211 "Нержавеющая сталь SUS630")
  (setq txt-211-1 "B"
        txt-211-2 "- материал стяжных болтов (гаек) нержавеющая сталь SUS630"
  );setq
);if

(if (= txt-211 "Нержавеющая сталь SUH660")
  (setq txt-211-1 "C"
        txt-211-2 "- материал стяжных болтов (гаек) нержавеющая сталь SUH660"
  );setq
);if

;//////////////////////////////////////////////////
(if (= txt-22 "Подвод имп. труб вертик., высок. давл. справа, присоединен. сверху")               
  (setq txt-22-1 "-2"
        txt-22-2 "- подвод импульсных труб вертикально,"
        txt-22-3 "высокое давление справа, присоединение сверху"
  );setq
);if

(if (= txt-22 "Подвод имп. труб вертик., высок. давл. справа, присоединен. снизу")               
  (setq txt-22-1 "-3"
        txt-22-2 "- подвод импульсных труб вертикально,"
        txt-22-3 "высокое давление справа, присоединение снизу"
  );setq
);if

(if (= txt-22 "Подвод имп. труб вертик., высок. давл. слева, присоединен. сверху")               
  (setq txt-22-1 "-6"
        txt-22-2 "- подвод импульсных труб вертикально,"
        txt-22-3 "высокое давление слева, присоединение сверху"
  );setq
);if

(if (= txt-22 "Подвод имп. труб вертик., высок. давл. слева, присоединен. снизу")               
  (setq txt-22-1 "-7"
        txt-22-2 "- подвод импульсных труб вертикально,"
        txt-22-3 "высокое давление слева, присоединение снизу"
  );setq
);if

(if (= txt-22 "Подвод имп. труб гориз., высок. давл. справа, присоединен. гориз.")               
  (setq txt-22-1 "-8"
        txt-22-2 "- подвод импульсных труб горизонтально,"
        txt-22-3 "высокое давление справа, присоединение горизонтально"
  );setq
);if

(if (= txt-22 "Подвод имп. труб гориз., высок. давл. слева, присоединен. гориз.")               
  (setq txt-22-1 "-9"
        txt-22-2 "- подвод импульсных труб горизонтально,"
        txt-22-3 "высокое давление слева, присоединение горизонтально"
  );setq
);if

;//////////////////////////////////////////////////
(if (= txt-221 "М20х1,5")               
  (setq txt-221-1 "4"
        txt-221-2 "- кабельный ввод М20х1,5"
  );setq
);if

(if (= txt-221 "G1/2 (BSP) ГОСТ 6357-81")               
  (setq txt-221-1 "5"
        txt-221-2 "- кабельный ввод G1/2 (BSP) ГОСТ 6357-81"
  );setq
);if

(if (= txt-221 "К1/2 (NPT) ГОСТ 6111-52")               
  (setq txt-221-1 "7"
        txt-221-2 "- кабельный ввод К1/2 (NPT) ГОСТ 6111-52"
  );setq
);if

(if (= txt-221 "Pg 13,5")               
  (setq txt-221-1 "8"
        txt-221-2 "- кабельный ввод Pg 13,5"
  );setq
);if

;//////////////////////////////////////////////////
(if (= txt-23 "Отсутствует") 
  (setq txt-23-1 "N"
        txt-23-2 "- индикатор отсутствует"
  );setq
);if

(if (= txt-23 "ЖК дисплей")
  (setq txt-23-1 "D"
        txt-23-2 "- индикатор стандартный"
  );setq
);if

(if (= txt-23 "ЖК дисплей, переключ. шкалы")
  (setq txt-23-1 "E"
        txt-23-2 "- индикатор стандартный, с переключателем шкалы"
  );setq
);if
  
;//////////////////////////////////////////////////
(if (= txt-31 "Нет")                  
  (setq txt-31-1 "N"
        txt-31-2 "- монтажный кронштейн нет"
  );setq
);if

(if (= txt-31 "Прямой, углеродистая сталь")
  (setq txt-31-1 "E"
        txt-31-2 "- монтажный кронштейн прямой, углеродистая сталь"
  );setq
);if

(if (= txt-31 "Прямой, нержавеющая сталь")
  (setq txt-31-1 "F"
        txt-31-2 "- монтажный кронштейн прямой, нержавеющая сталь"
  );setq
);if

(if (= txt-31 "Г-образный, углеродистая сталь")
  (setq txt-31-1 "E"
        txt-31-2 "- монтажный кронштейн Г-образный, углеродистая сталь"
  );setq
);if

(if (= txt-31 "Г-образный, нержавеющая сталь")
  (setq txt-31-1 "F"
        txt-31-2 "- монтажный кронштейн Г-образный, нержавеющая сталь"
  );setq
);if

;//////////////////////////////////////////////////
(if (= txt-18 "Стандартная") 
  (setq txt-18-1 ""
        txt-18-2 "- исполнение с нормальной точностью"
  );setq
);if

(if (= txt-18 "Повышенная")
  (setq txt-18-1 "/Z"
        txt-18-2 "- исполнение с повышенной точностью"
  );setq
);if

;//////////////////////////////////////////////////
(if (= txt-24 "Обычное, IP67")                  
  (setq txt-24-1 ""
        txt-24-2 "- без взрывозащиты, IP67"
  );setq
);if

(if (= txt-24 "0ExiaIICT5X")
  (setq txt-24-1 "/KS2"
        txt-24-2 "- 0ExiaIICT5X (искробезопасная цепь)"
  );setq
);if

(if (= txt-24 "1ExdIICT4...T6")
  (setq txt-24-1 "/KF2"
        txt-24-2 "- 1ExdIICT4...T6 (взрывонепроницаемая оболочка)"
  );setq
);if

;//////////////////////////////////////////////////
(if (= txt-41 "Нет")                  
  (setq txt-41-2 "- без вентильного блока"
  );setq
);if

(if (= txt-41 "3 вентиля, ниппеля под приварку")
  (setq txt-41-2 "- вентильный блок 3 вентиля, ниппеля под приварку"
  );setq
);if

(if (= txt-41 "5 вентилей, дренажные клапана, ниппеля под приварку")
  (setq txt-41-2 "- вентильный блок 5 вентилей, дренажные клапана, ниппеля под приварку"
  );setq
);if

(setq txt-ins-1 (strcat "EJA110A" txt-15-1 txt-17-1 txt-20-1 txt-21-1 txt-211-1 txt-22-1 txt-221-1 txt-23-1 txt-31-1 "/EP/QR")
      txt-ins-2 (strcat txt-18-1 txt-24-1)
);setq

;отрисовка строк спецификации
(101-empt-lin-spcf)
(setvar "osmode" 6199)
(setq pnt-ins		(getpoint "\nУкажите точку вставки\n")
	    x-pnt-ins (nth 0 pnt-ins)
	    y-pnt-ins (nth 1 pnt-ins)
	    ypnt-ins-1 y-pnt-ins
	    dlt-y 8
);setq
(setvar "osmode" 0)
(setvar "cmdecho" 0)
(repeat num-lin
  (command "_insert" "зс-пустая-строка" "_X" 1 "_Y" 1 "_Z" 1 "_R" 0 (list x-pnt-ins ypnt-ins-1))
  (setq ypnt-ins-1 (- ypnt-ins-1 8)
  );setq
);repeat

(command "_TEXT" "_ML" (list (+ x-pnt-ins 1) (- (- y-pnt-ins (* dlt-y 0)) 4)) 2.5 0 "Датчик разности давлений общего назначения");наименование

(command "_TEXT" "_ML" (list (+ x-pnt-ins 5) (- (- y-pnt-ins (* dlt-y 1)) 4)) 2.5 0 (strcat "- измеряемая среда " (strcase txt-10 4)))
(command "_TEXT" "_ML" (list (+ x-pnt-ins 5) (- (- y-pnt-ins (* dlt-y 2)) 4)) 2.5 0 (strcat "- температура измеряемой среды " txt-11 "..." txt-12 " %%dC"))
(command "_TEXT" "_ML" (list (+ x-pnt-ins 5) (- (- y-pnt-ins (* dlt-y 3)) 4)) 2.5 0 (strcat "- максимальное статическое давление " txt-121 " МПа"))
(command "_TEXT" "_ML" (list (+ x-pnt-ins 5) (- (- y-pnt-ins (* dlt-y 4)) 4)) 2.5 0 (strcat "- температура окружающей среды " txt-13 "..." txt-14 " %%dC"))
(command "_TEXT" "_ML" (list (+ x-pnt-ins 5) (- (- y-pnt-ins (* dlt-y 5)) 4)) 2.5 0 (strcat txt-15-2))
(command "_TEXT" "_ML" (list (+ x-pnt-ins 5) (- (- y-pnt-ins (* dlt-y 6)) 4)) 2.5 0 (strcat txt-16-1))
(command "_TEXT" "_ML" (list (+ x-pnt-ins 5) (- (- y-pnt-ins (* dlt-y 7)) 4)) 2.5 0 (strcat txt-17-2))
(command "_TEXT" "_ML" (list (+ x-pnt-ins 5) (- (- y-pnt-ins (* dlt-y 8)) 4)) 2.5 0 (strcat txt-17-3))
(command "_TEXT" "_ML" (list (+ x-pnt-ins 5) (- (- y-pnt-ins (* dlt-y 9)) 4)) 2.5 0 (strcat txt-20-2))
(command "_TEXT" "_ML" (list (+ x-pnt-ins 5) (- (- y-pnt-ins (* dlt-y 10)) 4)) 2.5 0 (strcat txt-20-3))
(command "_TEXT" "_ML" (list (+ x-pnt-ins 5) (- (- y-pnt-ins (* dlt-y 11)) 4)) 2.5 0 (strcat txt-21-2))
(command "_TEXT" "_ML" (list (+ x-pnt-ins 5) (- (- y-pnt-ins (* dlt-y 12)) 4)) 2.5 0 (strcat txt-21-3))
(command "_TEXT" "_ML" (list (+ x-pnt-ins 5) (- (- y-pnt-ins (* dlt-y 13)) 4)) 2.5 0 (strcat txt-211-2))
(command "_TEXT" "_ML" (list (+ x-pnt-ins 5) (- (- y-pnt-ins (* dlt-y 14)) 4)) 2.5 0 (strcat txt-22-2))
(command "_TEXT" "_ML" (list (+ x-pnt-ins 5) (- (- y-pnt-ins (* dlt-y 15)) 4)) 2.5 0 (strcat txt-22-3))
(command "_TEXT" "_ML" (list (+ x-pnt-ins 5) (- (- y-pnt-ins (* dlt-y 16)) 4)) 2.5 0 (strcat txt-221-2))
(command "_TEXT" "_ML" (list (+ x-pnt-ins 5) (- (- y-pnt-ins (* dlt-y 17)) 4)) 2.5 0 (strcat txt-23-2))
(command "_TEXT" "_ML" (list (+ x-pnt-ins 5) (- (- y-pnt-ins (* dlt-y 18)) 4)) 2.5 0 (strcat txt-18-2))
(command "_TEXT" "_ML" (list (+ x-pnt-ins 5) (- (- y-pnt-ins (* dlt-y 19)) 4)) 2.5 0 (strcat txt-24-2))
(command "_TEXT" "_ML" (list (+ x-pnt-ins 5) (- (- y-pnt-ins (* dlt-y 20)) 4)) 2.5 0 (strcat txt-31-2))
(command "_TEXT" "_ML" (list (+ x-pnt-ins 5) (- (- y-pnt-ins (* dlt-y 21)) 4)) 2.5 0 "- первично поверенный")
(command "_TEXT" "_ML" (list (+ x-pnt-ins 5) (- (- y-pnt-ins (* dlt-y 22)) 4)) 2.5 0 (strcat txt-41-2))

(command "_TEXT" "_MC" (list (+ x-pnt-ins 160) (- (- y-pnt-ins (* dlt-y 0)) 4)) 2.5 0 txt-ins-1);код заказа
(command "_TEXT" "_MC" (list (+ x-pnt-ins 160) (- (- y-pnt-ins (* dlt-y 1)) 4)) 2.5 0 txt-ins-2)

(command "_TEXT" "_MC" (list (+ x-pnt-ins 280) (- (- y-pnt-ins (* dlt-y 0)) 4)) 2.5 0 "шт.");количество

(command "_TEXT" "_MC" (list (+ x-pnt-ins 247.5) (- (- y-pnt-ins (* dlt-y 0)) 4)) 2.5 0 "\"ЭТАЛОН-ПРИБОР\",");производитель
(command "_TEXT" "_MC" (list (+ x-pnt-ins 247.5) (- (- y-pnt-ins (* dlt-y 1)) 4)) 2.5 0 "г. Челябинск")

(command "_TEXT" "_ML" (list (+ x-pnt-ins 336) (- (- y-pnt-ins (* dlt-y 0)) 4)) 2.5 0 "№14495-09 в Госреестре");сертификат
(command "_TEXT" "_ML" (list (+ x-pnt-ins 336) (- (- y-pnt-ins (* dlt-y 1)) 4)) 2.5 0 "средств измерений,")
(command "_TEXT" "_ML" (list (+ x-pnt-ins 336) (- (- y-pnt-ins (* dlt-y 2)) 4)) 2.5 0 "свидетельство,")
(command "_TEXT" "_ML" (list (+ x-pnt-ins 336) (- (- y-pnt-ins (* dlt-y 3)) 4)) 2.5 0 "об утверждении типа")
(command "_TEXT" "_ML" (list (+ x-pnt-ins 336) (- (- y-pnt-ins (* dlt-y 4)) 4)) 2.5 0 "средств измерений")
(command "_TEXT" "_ML" (list (+ x-pnt-ins 336) (- (- y-pnt-ins (* dlt-y 5)) 4)) 2.5 0 "JP.C.30.004.A №38504")
(command "_TEXT" "_ML" (list (+ x-pnt-ins 336) (- (- y-pnt-ins (* dlt-y 6)) 4)) 2.5 0 "от 15.03.2010г.,")
(command "_TEXT" "_ML" (list (+ x-pnt-ins 336) (- (- y-pnt-ins (* dlt-y 7)) 4)) 2.5 0 "разрешение")
(command "_TEXT" "_ML" (list (+ x-pnt-ins 336) (- (- y-pnt-ins (* dlt-y 8)) 4)) 2.5 0 "Ростехнадзора")
(command "_TEXT" "_ML" (list (+ x-pnt-ins 336) (- (- y-pnt-ins (* dlt-y 9)) 4)) 2.5 0 "на применение")
(command "_TEXT" "_ML" (list (+ x-pnt-ins 336) (- (- y-pnt-ins (* dlt-y 10)) 4)) 2.5 0 "№ РРС 00-32124")
(command "_TEXT" "_ML" (list (+ x-pnt-ins 336) (- (- y-pnt-ins (* dlt-y 11)) 4)) 2.5 0 "от 24.11.2008г.")

(setvar "osmode" 6199)
(setvar "cmdecho" 1)
(vla-endundomark adoc)
(princ)
)
;/////// конец программы ///////

;///////////////////////////////////////////////////////////////////////////////////////////////////////////////
;///////////////////////////////////////////////////////////////////////////////////////////////////////////////
;///////////////////////////////////////////////////////////////////////////////////////////////////////////////
(defun list-filling
(name-list data-list / )

(progn
  (start_list name-list)
  (mapcar 'add_list data-list)
  (end_list)
);progn

(princ)
)
;///////////////////////////////////////////////////////////////////////////////////////////////////////////////
;///////////////////////////////////////////////////////////////////////////////////////////////////////////////
;///////////////////////////////////////////////////////////////////////////////////////////////////////////////

;///////////////////////////////////////////////////////////////////////////////////////////////////////////////
;///////////////////////////////////////////////////////////////////////////////////////////////////////////////
;///////////////////////////////////////////////////////////////////////////////////////////////////////////////
(defun tmp-1-101-eja110a-etalon
($value / type-1)

(setq type-1 (nth (atoi $value) list-15)
);setq

(if (= "FOUNDATION Fieldbus" type-1)
  (setq list-24 (list "Обычное, IP67")
  );setq
);if

(if (/= "FOUNDATION Fieldbus" type-1)
  (setq list-24 (list "Обычное, IP67" "0ExiaIICT5X" "1ExdIICT4...T6")
  );setq
);if

(list-filling "txt-24" list-24)
(set_tile "txt-24" "0")

(princ)
)
;///////////////////////////////////////////////////////////////////////////////////////////////////////////////
;///////////////////////////////////////////////////////////////////////////////////////////////////////////////
;///////////////////////////////////////////////////////////////////////////////////////////////////////////////

;///////////////////////////////////////////////////////////////////////////////////////////////////////////////
;///////////////////////////////////////////////////////////////////////////////////////////////////////////////
;///////////////////////////////////////////////////////////////////////////////////////////////////////////////
(defun tmp-2-101-eja110a-etalon
($value / type-1 type-2)

(setq type-1 (nth (atoi $value) list-17)
);setq

(setq type-2 (nth (atoi (get_tile "txt-20")) list-20)
);setq

(if (and (= "SCS14A (фланцы), SUS316L (капусла), SUS316 (клапаны)" type-2)
         (= "-100...100 кПа (1...100)" type-1)
         );and
  (setq list-18 (list "Стандартная" "Повышенная")
  );setq
);if

(if (and (= "SCS14A (фланцы), SUS316L (капусла), SUS316 (клапаны)" type-2)
         (= "-500...500 кПа (5...500)" type-1)
         );and
  (setq list-18 (list "Стандартная" "Повышенная")
  );setq
);if

(if (and (= "SCS14A (фланцы), SUS316L (капусла), SUS316 (клапаны)" type-2)
         (= "-10...10 кПа (0,5...10)" type-1)
         );and
  (setq list-18 (list "Стандартная")
  );setq
);if

(if (and (= "SCS14A (фланцы), SUS316L (капусла), SUS316 (клапаны)" type-2)
         (= "-0,5...14 МПа (0,14...14)" type-1)
         );and
  (setq list-18 (list "Стандартная")
  );setq
);if

(list-filling "txt-18" list-18)
(set_tile "txt-18" "0")

(princ)
)
;///////////////////////////////////////////////////////////////////////////////////////////////////////////////
;///////////////////////////////////////////////////////////////////////////////////////////////////////////////
;///////////////////////////////////////////////////////////////////////////////////////////////////////////////

;///////////////////////////////////////////////////////////////////////////////////////////////////////////////
;///////////////////////////////////////////////////////////////////////////////////////////////////////////////
;///////////////////////////////////////////////////////////////////////////////////////////////////////////////
(defun tmp-3-101-eja110a-etalon
($value / type-1 type-2)

(setq type-1 (nth (atoi $value) list-20)
);setq

(setq type-2 (nth (atoi (get_tile "txt-17")) list-17)
);setq

(if (and (= "SCS14A (фланцы), SUS316L (капусла), SUS316 (клапаны)" type-1)
         (= "-100...100 кПа (1...100)" type-2)
         );and
  (setq list-18 (list "Стандартная" "Повышенная")
  );setq
);if

(if (and (= "SCS14A (фланцы), SUS316L (капусла), SUS316 (клапаны)" type-1)
         (= "-500...500 кПа (5...500)" type-2)
         );and
  (setq list-18 (list "Стандартная" "Повышенная")
  );setq
);if

(if (/= "SCS14A (фланцы), SUS316L (капусла), SUS316 (клапаны)" type-1)
  (setq list-18 (list "Стандартная")
  );setq
);if

(list-filling "txt-18" list-18)
(set_tile "txt-18" "0")

(princ)
)
;///////////////////////////////////////////////////////////////////////////////////////////////////////////////
;///////////////////////////////////////////////////////////////////////////////////////////////////////////////
;///////////////////////////////////////////////////////////////////////////////////////////////////////////////
