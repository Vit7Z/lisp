;/////// ************************************************************ ///////////////////////////////////////////////////////////////////////////////////////////////////////////
;/////// ведомость основных комплектов рабочих чертежей               ///////////////////////////////////////////////////////////////////////////////////////////////////////////
;/////// ************************************************************ ///////////////////////////////////////////////////////////////////////////////////////////////////////////
(defun c:02-main-sets-working-drawings-02-ins-header

( / adoc pnt-ins p-txt xpnt-ins ypnt-ins)

(setvar	"cmdecho" 0)
(setvar	"OSMODE" 6199)

(vl-load-com)
(vla-startundomark (setq adoc (vla-get-activedocument (vlax-get-acad-object))));undo

(load "d:\\yandexdisk\\my-sprt\\02-design\\02-main-sets-working-drawings-04-set-header.lsp") (02-main-sets-working-drawings-04-set-header) ;;;;;;;вед-осн-компл-рч-шапка

(setq pnt-ins (getpoint "\nУкажите точку вставки\n")
			xpnt-ins (nth 0 pnt-ins)
			ypnt-ins (nth 1 pnt-ins)
			p-txt (list (+ xpnt-ins 1) (- ypnt-ins 4)); точка вставки названия таблицы
);setq
		
(setvar	"OSMODE" 0)

(command "_TEXT" "_ML" p-txt 3.5 0 "Ведомость основных комплектов рабочих чертежей")

(command "_insert" "вед-осн-компл-рч-шапка" "_X" 1 "_Y" 1 "_Z" 1 "_R" 0 pnt-ins)

(setvar "osmode" 6199)
(setvar "cmdecho" 1)

(vla-endundomark adoc)

(gc)
(princ)
)
;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////
