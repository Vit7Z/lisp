;/////// ************************************************************ ///////////////////////////////////////////////////////////////////////////////////////////////////////////
;/////// штамп ГИП                                                    ///////////////////////////////////////////////////////////////////////////////////////////////////////////
;/////// ************************************************************ ///////////////////////////////////////////////////////////////////////////////////////////////////////////

(defun c:02-stamp-gip

( / pnt-1 pnt-txt txt txt-1 xpnt-1 ypnt-1)

(setvar	"osmode" 6199)
(setvar	"cmdecho" 0)

(setq pnt-1 (getpoint "\nУкажите точку вставки\n")
      xpnt-1 (nth 0 pnt-1)
      ypnt-1 (nth 1 pnt-1)
      pnt-txt (list (+ xpnt-1 100) (+ ypnt-1 15))
      txt (strcat "Технические решения, принятые в рабочих чертежах, соответствуют требованиям экологических, санитарно-гигиенических, "
      						"противопожарных и других норм, действующих на территории Российской Федерации, а также мер по предотвращению постороннего вмешательства "
      						"в ход технологических процессов и противодействию террористических проявлений, и обеспечивают безопасную для жизни и здоровья людей эксплуатацию объекта "
      						"при соблюдении предусмотренных рабочими чертежами мероприятий. \n"
      						"Главный инженер проекта______________ / ****** /")
);setq

(setvar	"OSMODE" 0)

(setq txt-1
  (entmakex
    (list
      '(0 . "MTEXT")
      '(100 . "AcDbEntity")
      '(100 . "AcDbMText")
       (cons 10 pnt-txt) ; нач точка текста
       (cons 1 txt) ; содержание текста
      '(40 . 2.5) ; высота текста
      '(41 . 200) ; растяжение текста
      '(42 . 200) ; ширина текста
      '(71 . 5) ; гориз выравнивание текста
      '(370 . -1) ; толщина текста
       (cons 7 (getvar "textstyle")) ; стиль текста
    ) ; end of list
  ); entmakex
); setq

(command "_RECTANGLE" pnt-1 (list (+ xpnt-1 200) (+ ypnt-1 30)))

(setvar "osmode" 6199)
(setvar "cmdecho" 1)

(princ)
)
;;;;/////////////////////////////////////////////////////////////////////////////////////////////////////////////////////////////////////////////////////////////////////////////
;;;;/////////////////////////////////////////////////////////////////////////////////////////////////////////////////////////////////////////////////////////////////////////////
