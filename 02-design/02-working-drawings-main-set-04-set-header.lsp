;/////// ************************************************************ /////////////////////////////////////////////////////////////////////////////////////////////////
;/////// ведомость рабочих чертежей основного комплекта, заголовок    /////////////////////////////////////////////////////////////////////////////////////////////////
;/////// ************************************************************ /////////////////////////////////////////////////////////////////////////////////////////////////
(defun 02-working-drawings-main-set-04-set-header

( / rctn-0 rctn-1 rctn-2 rctn-3 txt-1 txt-2 txt-3)

;устанавливаем системные переменные
(setvar	"cmdecho" 0)

; создаем слой wspom
(if (= (tblsearch "layer" "wspom") nil)
	(command "_layer" "_Make" "wspom" "_Color" 3 "wspom" "_L" "Continuous" "wspom"   "")
);if

(if (= (tblsearch "block" "вед-рч-осн-компл-шапка" ) nil)
	(progn				; если данного блока нет
		(setvar	"OSMODE" 0)
		(setvar	"CLAYER" "wspom")
		(setvar "CELWEIGHT" -1)
		
		(command "_RECTANGLE" '(0 0) '(8 -8))
		(setq rctn-0 (entlast))

		(setvar	"CLAYER" "0")
		(setvar "CELWEIGHT" 60)
		(command "_RECTANGLE" '(0 -8) '(15 -23))
		(setq rctn-1 (entlast))
		(command "_RECTANGLE" '(15 -8) '(155 -23))
		(setq rctn-2 (entlast))	
		(command "_RECTANGLE" '(155 -8) '(185 -23))	
		(setq rctn-3 (entlast))
		
  	(setvar "CELWEIGHT" -1)
		(command "_TEXT" "_MC" '(7.5 -15.5) 3.5 0 "Лист")
		(setq txt-1 (entlast))
		(command "_TEXT" "_MC" '(85 -15.5) 3.5 0 "Наименование")
		(setq txt-2 (entlast))
		(command "_TEXT" "_MC" '(170 -15.5) 3.5 0 "Примечание")
		(setq txt-3 (entlast))
		
		(command "_block" "вед-рч-осн-компл-шапка"  '(0 0)  rctn-0  rctn-1  rctn-2  rctn-3  txt-1  txt-2  txt-3 "")
	);progn
);if

(setvar "CMDECHO" 1)
(setvar	"ORTHOMODE" 1)
(setvar	"OSMODE" 6199)
(princ)
)
;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////
