;/////// ************************************************************ /////////////////////////////////////////////////////////////////////////////////////////////////
;/////// прилагаемые документы, са                                    /////////////////////////////////////////////////////////////////////////////////////////////////
;/////// ************************************************************ /////////////////////////////////////////////////////////////////////////////////////////////////
(defun c:02-enclosed-doc-01-ins-documents

( / adoc lin-1 lin-2 lin-3 lin-4 lin-5 lin-6 lin-7 pnt-ins xpnt-ins ypnt-ins)

;устанавливаем системные переменные
(setvar	"CMDECHO" 0)
(setvar	"OSMODE" 6199)

(vl-load-com)
(vla-startundomark (setq adoc (vla-get-activedocument (vlax-get-acad-object))));start undo

(setq pnt-ins (getpoint "\nУкажите точку вставки\n")
			xpnt-ins (nth 0 pnt-ins)
			ypnt-ins (nth 1 pnt-ins)
);setq
		
(setvar	"OSMODE" 0)
		
(command "_TEXT" "_MC" (list (+ xpnt-ins 47.5) (- ypnt-ins 4)) 2.5 0 "%%UПрилагаемые документы")
(command "_insert" "вед-осн-компл-рч-строка" "_X" 1 "_Y" 1 "_Z" 1 "_R" 0 pnt-ins)

(vla-endundomark adoc)

(setvar "CMDECHO" 1)
(setvar	"ORTHOMODE" 1)
(setvar	"OSMODE" 6199)
(princ)
)
;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////
