;/////// ************************************************************ /////////////////////////////////////////////////////////////////////////////////////////////////
;/////// ведомость ссылочных и прилагаемых документов, строка         /////////////////////////////////////////////////////////////////////////////////////////////////
;/////// ************************************************************ /////////////////////////////////////////////////////////////////////////////////////////////////
(defun 02-working-drawings-main-set-05-set-empty-line

( / lin-1 lin-2 lin-3 lin-4 lin-5 lin-6 lin-7)

;устанавливаем системные переменные
(setvar	"CMDECHO" 0)
(setvar	"OSMODE" 0)

(if (= (tblsearch "block" "вед-рч-осн-компл-строка" ) nil)
	(progn				; если данного блока нет	
		(setvar	"CLAYER" "0")
		(setvar "CELWEIGHT" 60)
		(command "_.line" '(-15 0) '(-15 -8) "")
		(setq lin-1 (entlast))
		(command "_.line" '(0 0) '(0 -8) "")
		(setq lin-2 (entlast))
		(command "_.line" '(140 0) '(140 -8) "")
		(setq lin-3 (entlast))
		(command "_.line" '(170 0) '(170 -8) "")
		(setq lin-4 (entlast))
		
		(setvar "CELWEIGHT" -1)
		(command "_.line" '(-15 -8) '(0 -8) "")
		(setq lin-5 (entlast))
		(command "_.line" '(0 -8) '(140 -8) "")
		(setq lin-6 (entlast))
		(command "_.line" '(140 -8) '(170 -8) "")
		(setq lin-7 (entlast))
		
		(command "_block" "вед-рч-осн-компл-строка" '(0 0) lin-1 lin-2 lin-3 lin-4 lin-5 lin-6 lin-7 "")
	);progn
);if

(setvar "CMDECHO" 1)
(setvar	"ORTHOMODE" 1)
(setvar	"OSMODE" 6199)
(princ)
)
;/////// *************************************************************/////////////////////////////////////////////////////////////////////////////////////////////////
;/////// КОНЕЦ ПРОГРАММЫ                                              /////////////////////////////////////////////////////////////////////////////////////////////////
;/////// *************************************************************/////////////////////////////////////////////////////////////////////////////////////////////////
