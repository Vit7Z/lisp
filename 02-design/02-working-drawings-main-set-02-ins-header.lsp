;/////// ************************************************************ ///////////////////////////////////////////////////////////////////////////////////////////////////////////
;/////// ведомость рабочих чертежей основного комплекта рабочих чертежей ////////////////////////////////////////////////////////////////////////////////////////////////////////
;/////// ************************************************************ ///////////////////////////////////////////////////////////////////////////////////////////////////////////
(defun c:02-working-drawings-main-set-02-ins-header

( / adoc pnt-ins p-txt xpnt-ins ypnt-ins)

(setvar	"cmdecho" 0)

(vl-load-com)
(vla-startundomark (setq adoc (vla-get-activedocument (vlax-get-acad-object))));undo

(load "d:\\mcloud\\my-sprt\\02-design\\02-working-drawings-main-set-04-set-header.lsp") (02-working-drawings-main-set-04-set-header) ;;;;;;;вед-рч-осн-компл-шапка

(setvar	"OSMODE" 6199)
		
(setq pnt-ins (getpoint "\nУкажите точку вставки\n"));setq
		
(setq xpnt-ins (nth 0 pnt-ins)
			ypnt-ins (nth 1 pnt-ins)
			p-txt (list (+ xpnt-ins 1) (- ypnt-ins 4)); точка вставки названия таблицы
);setq
		
(setvar	"OSMODE" 0)
		
(command "_TEXT" "_ML" p-txt 3.5 0 "Ведомость рабочих чертежей основного комплекта")
		
(command "_insert" "вед-рч-осн-компл-шапка" "_X" 1 "_Y" 1 "_Z" 1 "_R" 0 pnt-ins)

(setvar "osmode" 6199)
(setvar "cmdecho" 1)
(vla-endundomark adoc)
(gc)
(princ)
)
;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////
