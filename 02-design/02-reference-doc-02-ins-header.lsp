;/////// ************************************************************ /////////////////////////////////////////////////////////////////////////////////////////////////
;/////// выбор ссылочных и прилагаемых документов, са                 /////////////////////////////////////////////////////////////////////////////////////////////////
;/////// ************************************************************ /////////////////////////////////////////////////////////////////////////////////////////////////
(defun c:02-reference-doc-02-ins-header

( / adoc pnt-ins xpnt-ins ypnt-ins)

(vl-load-com)
(vla-startundomark (setq adoc (vla-get-activedocument (vlax-get-acad-object))));start undo

;устанавливаем системные переменные
(setvar	"OSMODE" 6199)
(setvar	"CMDECHO" 0)

;только шапка таблицы /////////////////////////////////////////////////////////////////////////////////////////////////////////////////////////////////////////////////
(setvar	"OSMODE" 6199)

(setq pnt-ins (getpoint "\nУкажите точку вставки\n")
			xpnt-ins (nth 0 pnt-ins)
			ypnt-ins (nth 1 pnt-ins)
);setq
		
(setvar	"OSMODE" 0)
		
(command "_TEXT" "_ML" (list (+ xpnt-ins 1) (- ypnt-ins 4)) 3.5 0 "Ведомость ссылочных и прилагаемых документов")
(command "_TEXT" "_MC" (list (+ xpnt-ins 107.5) (- ypnt-ins 27)) 2.5 0 "%%UСсылочные документы")

(command "_insert" "вед-осн-компл-рч-шапка" "_X" 1 "_Y" 1 "_Z" 1 "_R" 0 pnt-ins)
(command "_insert" "вед-осн-компл-рч-строка" "_X" 1 "_Y" 1 "_Z" 1 "_R" 0 (list (+ xpnt-ins 60) (- ypnt-ins 23)))

(vla-endundomark adoc)

(setvar "CMDECHO" 1)
(setvar	"ORTHOMODE" 1)
(setvar	"OSMODE" 6199)
(princ)
)
;/////// *************************************************************/////////////////////////////////////////////////////////////////////////////////////////////////
;/////// КОНЕЦ ПРОГРАММЫ                                              /////////////////////////////////////////////////////////////////////////////////////////////////
;/////// *************************************************************/////////////////////////////////////////////////////////////////////////////////////////////////
