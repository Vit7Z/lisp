;/////// ************************************************************ //////////////////////////////
;/////// выбор ссылочных и прилагаемых документов, заголовок          //////////////////////////////
;/////// ************************************************************ //////////////////////////////
(defun 02-main-sets-working-drawings-04-set-header

( / rctn-1 rctn-2 rctn-3 txt-1 txt-2 txt-3)

;устанавливаем системные переменные
(setvar	"cmdecho" 0)

(if (= (tblsearch "block" "вед-осн-компл-рч-шапка" ) nil)
	(progn				; если данного блока нет
		(setvar	"OSMODE" 0)
		(setvar	"CLAYER" "0")
		(setvar "CELWEIGHT" 60)
		(command "_RECTANGLE" '(0 -8) '(60 -23))
		(setq rctn-1 (entlast))
		(command "_RECTANGLE" '(60 -8) '(155 -23))
		(setq rctn-2 (entlast))	
		(command "_RECTANGLE" '(155 -8) '(185 -23))	
		(setq rctn-3 (entlast))
		
  	(setvar "CELWEIGHT" -1)
		(command "_TEXT" "_MC" '(30 -15.5) 3.5 0 "Обозначение")
		(setq txt-1 (entlast))
		(command "_TEXT" "_MC" '(107.5 -15.5) 3.5 0 "Наименование")
		(setq txt-2 (entlast))
		(command "_TEXT" "_MC" '(170 -15.5) 3.5 0 "Примечание")
		(setq txt-3 (entlast))
		
		(command "_block" "вед-осн-компл-рч-шапка" '(0 0)  rctn-1  rctn-2  rctn-3  txt-1  txt-2  txt-3 "")
	);progn
);if

(setvar "CMDECHO" 1)
(setvar	"ORTHOMODE" 1)
(setvar	"OSMODE" 6199)
(princ)
)
;/////// *************************************************************//////////////////////////////
;/////// КОНЕЦ ПРОГРАММЫ                                              //////////////////////////////
;/////// *************************************************************//////////////////////////////
