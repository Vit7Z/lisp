;/////// ************************************************************ /////////////////////////////////////////////////////////////////////////////////////////////////////////////////////////////////////////
;///////                                                              /////////////////////////////////////////////////////////////////////////////////////////////////////////////////////////////////////////
;/////// ************************************************************ /////////////////////////////////////////////////////////////////////////////////////////////////////////////////////////////////////////
(defun 101-01-exec-mech-pem-b

( / adoc dcl-id file-name file-open list-00 list-01 list-02 list-03 list-04 list-05 list-06 list-07 list-08 list-09 list-901 list-902 path-file-open str-0 str-1 str-2 str-3 str-f type-list)

(vl-load-com)
(vla-startundomark
  (setq adoc (vla-get-activedocument (vlax-get-acad-object))
  );setq
);start undo

(setq str-f 1;переменные
			str-0 nil
			str-1 nil
			str-2 nil
			str-3 nil
      list-901 nil
      list-902 nil
			file-name nil
			file-open nil
			path-file-open nil
);setq

(start-101-01-exec-mech-pem-b)

(if (< (setq dcl-id (load_dialog "dia-101-01-exec-mech-pem-a.dcl")) 0) ;ищем диалог
		(progn
			(alert "Не найден dcl-файл")
			(exit)
		);progn
);if

(if (not (new_dialog "dia_101_01_exec_mech_pem_a" dcl-id))
		(exit)
);if

(list-filling "txt-00" list-00)
(list-filling "txt-01" list-01)
(list-filling "txt-02" list-02)
(list-filling "txt-03" list-03)
(list-filling "txt-04" list-04)
(list-filling "txt-05" list-05)
(list-filling "txt-06" list-06)
(list-filling "txt-07" list-07)
(list-filling "txt-08" list-08)
(list-filling "txt-09" list-09)

(set_tile "txt-00" "0")
(set_tile "txt-01" "0")
(set_tile "txt-02" "0")
(set_tile "txt-03" "0")
(set_tile "txt-04" "0")
(set_tile "txt-05" "0")
(set_tile "txt-06" "0")
(set_tile "txt-07" "0")
(set_tile "txt-08" "0")
(set_tile "txt-09" "0")

(action_tile "txt-00"
  (strcat "(txt-00-101-01-exec-mech-pem-b)"
  );srcat
);action_tile

(action_tile "txt-01"
  (strcat "(txt-01-101-01-exec-mech-pem-b)"
  );srcat
);action_tile

(action_tile "txt-02"
  (strcat "(txt-02-101-01-exec-mech-pem-b)"
  );srcat
);action_tile

(action_tile "txt-03"
  (strcat "(txt-03-101-01-exec-mech-pem-b)"
  );srcat
);action_tile

(action_tile "txt-04"
  (strcat "(txt-04-101-01-exec-mech-pem-b)"
  );srcat
);action_tile

(action_tile "txt-05"
  (strcat "(txt-05-101-01-exec-mech-pem-b)"
  );srcat
);action_tile


(action_tile "but1"
  (strcat "(but1-101-01-exec-mech-pem-b)"
  );strcat
);action_tile

(action_tile "but2"
  (strcat "(setq type-list \"le\")"
          "(done_dialog)"
  );strcat
);action_tile

(action_tile "but3"
  (strcat "(setq type-list \"spcf\")"
          "(done_dialog)"
  );strcat
);action_tile

(action_tile "accept"
  (strcat "(done_dialog)"
          "(exit)"
  );strcat
);action_tile

(start_dialog)
(unload_dialog dcl-id)

(cond
	((= type-list "le") (le-101-01-exec-mech-pem-b));=
	((= type-list "spcf") (spcf-101-01-exec-mech-pem-b));=
);cond

(setvar "osmode" 6199)
(setvar "cmdecho" 1)
(vla-endundomark adoc)
(gc)
(princ)
)
;/////// конец программы ////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun start-101-01-exec-mech-pem-b

( / file-open path-file-open str-f str-lft-00 str-lft-01 str-lft-02 str-lft-03 str-lft-04 str-lft-05 str-lft-06 str-lft-09)

(setq str-f 1
			str-lft-00 nil
			str-lft-01 nil
			str-lft-02 nil
			str-lft-03 nil
			str-lft-04 nil
			str-lft-05 nil
			str-lft-06 nil
			str-lft-09 nil
			list-01 nil
			list-02 nil
			list-03 nil
			list-04 nil
			list-05 nil
			list-06 (list "М Блок концевых выключателей" 
										"У Токовый датчик сигнализации положения"
										"КИМ1-3-А-380 Аналоговое управление"
										"КИМ1-3-Д-380 Дискретное управление"
										"КИМ1-3-С-380 Сетевое управление"
										"КИМ1-3-Т-380 Дискретно-сетевое управление")
			list-09 nil
);setq

(setq path-file-open (findfile "101-01-exec-mech-pem-b.txt");открываем файл, создаем список для занесения в диалог
			file-open (open path-file-open "r")
);setq

(while (/= str-f nil)
	(setq str-f (read-line file-open);читаем строку
	);setq
	(if (/= str-f nil)
		(setq str-lft-00 (substr str-f 1 (vl-string-search "\\" str-f))
					str-f (substr str-f (+ (vl-string-search "\\" str-f) 2));2 \\
					str-lft-01 (substr str-f 1 (vl-string-search "\\" str-f))
					str-f (substr str-f (+ (vl-string-search "\\" str-f) 2));2 \\
					str-lft-02 (substr str-f 1 (vl-string-search "\\" str-f))
					str-f (substr str-f (+ (vl-string-search "\\" str-f) 2));3 \\
					str-lft-03 (substr str-f 1 (vl-string-search "\\" str-f))
					str-f (substr str-f (+ (vl-string-search "\\" str-f) 2));13 \\
					str-lft-04 (substr str-f 1 (vl-string-search "\\" str-f))
					str-f (substr str-f (+ (vl-string-search "\\" str-f) 2));13 \\
					str-lft-05 (substr str-f 1 (vl-string-search "\\" str-f))
					str-f (substr str-f (+ (vl-string-search "\\" str-f) 2));13 \\
					str-lft-09 (substr str-f 1 (vl-string-search "\\" str-f))
					list-00 (vl-list* str-lft-00 list-00);создаем список из считанных строк из файла
					list-01 (vl-list* str-lft-01 list-01)
					list-02 (vl-list* str-lft-02 list-02)
					list-03 (vl-list* str-lft-03 list-03)
					list-04 (vl-list* str-lft-04 list-04)
					list-05 (vl-list* str-lft-05 list-05)
					list-09 (vl-list* str-lft-09 list-09)					
		);setq
	);if
);while

(close file-open)

(setq list-00 (reverse (vl-remove "" list-00))
			list-01 (reverse (vl-remove "" list-01))
      list-02 (reverse (vl-remove "" list-02))
      list-03 (reverse (vl-remove "" list-03))
      list-04 (reverse (vl-remove "" list-04))
      list-05 (reverse (vl-remove "" list-05))
      list-09 (reverse (vl-remove "" list-09))
);setq

(list-filling "txt-00" list-00)
(list-filling "txt-01" list-01)
(list-filling "txt-02" list-02)
(list-filling "txt-03" list-03)
(list-filling "txt-04" list-04)
(list-filling "txt-05" list-05)
(list-filling "txt-06" list-06)
(list-filling "txt-09" list-09)

(set_tile "txt-00" "0")
(set_tile "txt-01" "0")
(set_tile "txt-02" "0")
(set_tile "txt-03" "0")
(set_tile "txt-04" "0")
(set_tile "txt-05" "0")
(set_tile "txt-06" "0")
(set_tile "txt-09" "0")

(princ)
)
;;;;/////////////////////////////////////////////////////////////////////////////////////////////////////////////////////////////////////////////////////////////////////////////
;;;;/////////////////////////////////////////////////////////////////////////////////////////////////////////////////////////////////////////////////////////////////////////////


;;;;/////////////////////////////////////////////////////////////////////////////////////////////////////////////////////////////////////////////////////////////////////////////
;;;; txt-00 /////////////////////////////////////////////////////////////////////////////////////////////////////////////////////////////////////////////////////////////////////
(defun txt-00-101-01-exec-mech-pem-b

( / str-00 str-00-1)

(setq str-00 (get_tile "txt-00")
			str-00-1 (nth (atoi (get_tile "txt-00")) list-00)
);setq

(set_tile "txt-01" str-00)
(set_tile "txt-02" str-00)
(set_tile "txt-03" str-00)
(set_tile "txt-04" str-00)
(set_tile "txt-05" str-00)
(set_tile "txt-09" str-00)

(princ)
)
;;;;/////////////////////////////////////////////////////////////////////////////////////////////////////////////////////////////////////////////////////////////////////////////
;;;;/////////////////////////////////////////////////////////////////////////////////////////////////////////////////////////////////////////////////////////////////////////////


;;;;/////////////////////////////////////////////////////////////////////////////////////////////////////////////////////////////////////////////////////////////////////////////
;;;; txt-01 /////////////////////////////////////////////////////////////////////////////////////////////////////////////////////////////////////////////////////////////////////
(defun txt-01-101-01-exec-mech-pem-b

( / str-00 str-00-1)

(setq str-00 (get_tile "txt-01")
);setq

(set_tile "txt-00" str-00)
(set_tile "txt-02" str-00)
(set_tile "txt-03" str-00)
(set_tile "txt-04" str-00)
(set_tile "txt-05" str-00)
(set_tile "txt-09" str-00)

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;; txt-02 /////////////////////////////////////////////////////////////////////////////////////////////////////////////////////////////////////////////////////////////////////
(defun txt-02-101-01-exec-mech-pem-b

( / str-00 str-00-1)

(setq str-00 (get_tile "txt-02")
);setq

(set_tile "txt-00" str-00)
(set_tile "txt-01" str-00)
(set_tile "txt-03" str-00)
(set_tile "txt-04" str-00)
(set_tile "txt-05" str-00)
(set_tile "txt-09" str-00)

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;; txt-03 /////////////////////////////////////////////////////////////////////////////////////////////////////////////////////////////////////////////////////////////////////
(defun txt-03-101-01-exec-mech-pem-b

( / str-00 str-00-1)

(setq str-00 (get_tile "txt-03")
);setq

(set_tile "txt-00" str-00)
(set_tile "txt-01" str-00)
(set_tile "txt-02" str-00)
(set_tile "txt-04" str-00)
(set_tile "txt-05" str-00)
(set_tile "txt-09" str-00)

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;; txt-04 /////////////////////////////////////////////////////////////////////////////////////////////////////////////////////////////////////////////////////////////////////
(defun txt-04-101-01-exec-mech-pem-b

( / str-00 str-00-1)

(setq str-00 (get_tile "txt-04")
);setq

(set_tile "txt-00" str-00)
(set_tile "txt-01" str-00)
(set_tile "txt-02" str-00)
(set_tile "txt-03" str-00)
(set_tile "txt-05" str-00)
(set_tile "txt-09" str-00)

(princ)
)
;;;;/////////////////////////////////////////////////////////////////////////////////////////////////////////////////////////////////////////////////////////////////////////////
;;;;/////////////////////////////////////////////////////////////////////////////////////////////////////////////////////////////////////////////////////////////////////////////


;;;;/////////////////////////////////////////////////////////////////////////////////////////////////////////////////////////////////////////////////////////////////////////////
;;;; txt-05 /////////////////////////////////////////////////////////////////////////////////////////////////////////////////////////////////////////////////////////////////////
(defun txt-05-101-01-exec-mech-pem-b

( / str-00 str-00-1)

(setq str-00 (get_tile "txt-05")
);setq

(set_tile "txt-00" str-00)
(set_tile "txt-01" str-00)
(set_tile "txt-02" str-00)
(set_tile "txt-03" str-00)
(set_tile "txt-04" str-00)
(set_tile "txt-09" str-00)

(setq str-00-1 (nth (atoi (get_tile "txt-00")) list-00)
);setq

(cond
	((= str-00-1 "А16") (setq list-06 (list "М Блок концевых выключателей")));=
	((= str-00-1 "А17") (setq list-06 (list "Р Реостатный датчик сигнализации положения")));=
	((= str-00-1 "А18") (setq list-06 (list "У Токовый датчик сигнализации положения")));=
	((= str-00-1 "А19") (setq list-06 (list "И Индуктивный датчик сигнализации положения")));=
	((setq list-06 (list "М Блок концевых выключателей" 
											 "У Токовый датчик сигнализации положения" 
											 "КИМ1-3-А-380 Аналоговое управление"
											 "КИМ1-3-Д-380 Дискретное управление"
											 "КИМ1-3-С-380 Сетевое управление"
											 "КИМ1-3-Т-380 Дискретно-сетевое управление")));=
);cond

(list-filling "txt-06" list-06)

(set_tile "txt-06" "0")

(princ)
)
;;;;/////////////////////////////////////////////////////////////////////////////////////////////////////////////////////////////////////////////////////////////////////////////
;;;;/////////////////////////////////////////////////////////////////////////////////////////////////////////////////////////////////////////////////////////////////////////////


;;;;///////////////////////////////////////////////////////////////////////////////////////////////////////////////////////////////////////////////////////////////////////////////////////////////////////////
;;;;подпрограмма формирования данных///////////////////////////////////////////////////////////////////////////////////////////////////////////////////////////////////////////////////////////////////////////
(defun but1-101-01-exec-mech-pem-b

( / str-00 str-01 str-02 str-03 str-04 str-05 str-06 str-99 swtch tmp-list-902)

;заполняем поле "выбрано"
(setq str-00 (nth (atoi (get_tile "txt-00")) list-00)
      swtch list-901 ;запоминаем первоначальное состояние списка в поле "выбрано"
);setq

(if (/= swtch nil)	;если есть уже выбраннное то переворачиваем
	(setq list-902 (reverse list-902)
	);setq
);if

(setq str-01 (nth (atoi (get_tile "txt-01")) list-01);считываем выбранные данные
			str-02 (nth (atoi (get_tile "txt-02")) list-02)
			str-03 (nth (atoi (get_tile "txt-03")) list-03)
			str-04 (nth (atoi (get_tile "txt-04")) list-04)
			str-05 (nth (atoi (get_tile "txt-05")) list-05)
			str-06 (nth (atoi (get_tile "txt-06")) list-06)
			str-99 (nth (atoi (get_tile "txt-09")) list-09)
);setq

(setq list-901 (vl-list* (strcat "ПЭМ-" str-00 "  " 
																 "Момент " str-01 "Нм  " 
																 "Частота вращения " str-02 "об/мин  " 
																 "Число оборотов " str-03 "  " 
																 "Потр. мощность " str-04 "кВт  " 
																 "Выходной вал " str-05 "  " 
																 str-06) list-901)
);setq

(setq tmp-list-902 (list (cons 0 str-00) (cons 1 str-01) (cons 2 str-02) (cons 3 str-03) (cons 4 str-04) (cons 5 str-05) (cons 6 str-06) (cons 99 str-99))
			list-902 (vl-list*  tmp-list-902 list-902)
);setq

(cond
	((= swtch nil) (setq list-902 (reverse list-902)));=
	((/= swtch nil) (setq list-902 (reverse list-902)));=
);cond

(list-filling "txt-901" (reverse list-901))

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;подпрограмма вывода в ПЭ                   //////////////////////////////////////////////////////////////////////////////////////////////////////////////////////////////////
(defun le-101-01-exec-mech-pem-b

( / cntr-1 dlt-y nmbr-ln pnt-ins str-0 str-6 str-61 str-tmp x-pnt-ins y-pnt-ins y-pnt-ins-1)

(setq cntr-1 0 ;счетчик
);setq

(repeat (length list-902)
	(setq str-tmp (nth cntr-1 list-902)
				str-0 (cdr (assoc 0 str-tmp))
				str-6 (cdr (assoc 6 str-tmp))
	);setq
	
;(princ "\n         str-tmp = ") (princ str-tmp);Erase_DV
;(getstring "\nPress Enter to continue...");Erase_DV
	
	(cond
		((= str-6 "М Блок концевых выключателей") (setq str-6 "М" str-61 "с блоком концевых выключателей"));=
		((= str-6 "Р Реостатный датчик сигнализации положения") (setq str-6 "Р" str-61 "с реостатным датчиком сигнализации положения"));=
		((= str-6 "И Индуктивный датчик сигнализации положения") (setq str-6 "И" str-61 "с индуктивным датчиком сигнализации положения"));=
		((= str-6 "У Токовый датчик сигнализации положения") (setq str-6 "У" str-61 "с токовым датчиком сигнализации положения"));=
		
		((= str-6 "КИМ1-3-А-380 Аналоговое управление") (setq str-6 "Е" str-61 "с контроллером КИМ1-3-А-380 (аналоговое управление)"));=
		((= str-6 "КИМ1-3-Д-380 Дискретное управление") (setq str-6 "Е" str-61 "с контроллером КИМ1-3-Д-380 (дискретое управление)"));=
		((= str-6 "КИМ1-3-С-380 Сетевое управление") (setq str-6 "Е" str-61 "с контроллером КИМ1-3-С-380 (сетевое управление)"));=
		((= str-6 "КИМ1-3-Т-380 Дискретно-сетевое управление") (setq str-6 "Е" str-61 "с контроллером КИМ1-3-Т-380 (дискретно-сетевое управление)"));=
	);cond

	(setvar "osmode" 6199)
	(setq pnt-ins		(getpoint "\nУкажите точку вставки\n")
  			x-pnt-ins (nth 0 pnt-ins)
 				y-pnt-ins (nth 1 pnt-ins)
  			y-pnt-ins-1 y-pnt-ins
  			dlt-y 8
  			nmbr-ln 3
	);setq
	
	(100-empt-lin-le)
	(setvar "osmode" 0)
	(setvar "cmdecho" 0)
		
	(1000-delete-items-le nmbr-ln x-pnt-ins y-pnt-ins)
			
	(command "_text" "_ML" (list (+ x-pnt-ins 1) (- (- y-pnt-ins (* dlt-y 0)) 4)) 2.5 0 (strcat "Электрический исполнительный механизм ПЭМ-" str-0 str-6 ","))
	(command "_text" "_ML" (list (+ x-pnt-ins 1) (- (- y-pnt-ins (* dlt-y 1)) 4)) 2.5 0 (strcat str-61))
	
	(setq cntr-1 (1+ cntr-1);счетчик
	);setq
	
	(repeat nmbr-ln
  	(command "_insert" "пэ-пустая-строка" "_X" 1 "_Y" 1 "_Z" 1 "_R" 0 (list x-pnt-ins y-pnt-ins-1))
  	(setq y-pnt-ins-1 (- y-pnt-ins-1 8)
  	);setq
	);repeat
);repeat

(princ)
)
;;;;///////////////////////////////////////////////////////////////////////////////////////////////////////////////////////////////////////////////////////////////////////////////////////////////////////////
;;;;///////////////////////////////////////////////////////////////////////////////////////////////////////////////////////////////////////////////////////////////////////////////////////////////////////////

;;;;///////////////////////////////////////////////////////////////////////////////////////////////////////////////////////////////////////////////////////////////////////////////////////////////////////////
;;;;подпрограмма вывода в спцф                   //////////////////////////////////////////////////////////////////////////////////////////////////////////////////////////////////////////////////////////////
(defun spcf-101-01-exec-mech-pem-b

( / cntr-1 dlt-y nmbr-ln pnt-ins str-0 str-1 str-2 str-3 str-4 str-5 str-6 str-61 str-99 str-tmp x-pnt-ins y-pnt-ins y-pnt-ins-1)

(setq cntr-1 0 ;счетчик
);setq

(repeat (length list-902)
	(setq str-tmp (nth cntr-1 list-902)
				str-0 (cdr (assoc 0 str-tmp))
				str-1 (cdr (assoc 1 str-tmp))
				str-2 (cdr (assoc 2 str-tmp))
				str-3 (cdr (assoc 3 str-tmp))
				str-4 (cdr (assoc 4 str-tmp))
				str-5 (cdr (assoc 5 str-tmp))
				str-6 (cdr (assoc 6 str-tmp))
				str-99 (cdr (assoc 99 str-tmp))
	);setq
	
	(setvar "osmode" 6199)
	(setq pnt-ins		(getpoint "\nУкажите точку вставки\n")
	  		x-pnt-ins (nth 0 pnt-ins)
	 			y-pnt-ins (nth 1 pnt-ins)
	  		y-pnt-ins-1 y-pnt-ins
	  		dlt-y 8
	); setq
	
	(101-empt-lin-spcf)
	(setvar "osmode" 0)
	(setvar "cmdecho" 0)

	;обработка данных
	(cond
		((= str-5 "Круг, диам. 44мм") (setq str-5 "круглого сечения, диаметром 44мм"));=
		((= str-5 "Квадрат, сторона 19мм") (setq str-5 "квадратного сечения, сторона 19мм"));=
	);cond

	(cond
		((= str-6 "М Блок концевых выключателей") (setq str-6 "М" str-61 "- блок концевых выключателей"));=
		((= str-6 "Р Реостатный датчик сигнализации положения") (setq str-6 "Р" str-61 "- реостатный датчик сигнализации положения"));=
		((= str-6 "И Индуктивный датчик сигнализации положения") (setq str-6 "И" str-61 "- индуктивный датчик сигнализации положения"));=
		((= str-6 "У Токовый датчик сигнализации положения") (setq str-6 "У" str-61 "- токовый датчик сигнализации положения"));=
		
		((= str-6 "КИМ1-3-А-380 Аналоговое управление") (setq str-6 "Е" str-61 "- контроллер КИМ1-3-А-380 (аналоговое управление)"));=
		((= str-6 "КИМ1-3-Д-380 Дискретное управление") (setq str-6 "Е" str-61 "- контроллер КИМ1-3-А-380 (дискретое управление)"));=
		((= str-6 "КИМ1-3-С-380 Сетевое управление") (setq str-6 "Е" str-61 "- контроллер КИМ1-3-А-380 (сетевое управление)"));=
		((= str-6 "КИМ1-3-Т-380 Дискретно-сетевое управление") (setq str-6 "Е" str-61 "- контроллер КИМ1-3-А-380 (дискретно-сетевое управление)"));=
	);cond
	
	(setq nmbr-ln 10);setq
	
	(1000-delete-items-spcf nmbr-ln x-pnt-ins y-pnt-ins);удаление предыдущей записи
	
	(command "_text" "_ML" (list (+ x-pnt-ins 1) (- (- y-pnt-ins (* dlt-y 0)) 4)) 2.5 0 "Электрический исполнительный механизм")
	(command "_text" "_ML" (list (+ x-pnt-ins 5) (- (- y-pnt-ins (* dlt-y 1)) 4)) 2.5 0 (strcat "- номинальный крутящий момент на выходном валу " str-1 "Нм"))
	(command "_text" "_ML" (list (+ x-pnt-ins 5) (- (- y-pnt-ins (* dlt-y 2)) 4)) 2.5 0 (strcat "- частота вращения выходного вала " str-2 "об/мин"))
	(command "_text" "_ML" (list (+ x-pnt-ins 5) (- (- y-pnt-ins (* dlt-y 3)) 4)) 2.5 0 (strcat "- число оборотов до открытия (закрытия) " str-3))
	(command "_text" "_ML" (list (+ x-pnt-ins 5) (- (- y-pnt-ins (* dlt-y 4)) 4)) 2.5 0 (strcat "- выходной вал " str-5))
	(command "_text" "_ML" (list (+ x-pnt-ins 5) (- (- y-pnt-ins (* dlt-y 5)) 4)) 2.5 0 "- электропитание двигателя напряжением 380В частотой 50 Гц")
	(command "_text" "_ML" (list (+ x-pnt-ins 5) (- (- y-pnt-ins (* dlt-y 6)) 4)) 2.5 0 str-61)
	(command "_text" "_ML" (list (+ x-pnt-ins 5) (- (- y-pnt-ins (* dlt-y 7)) 4)) 2.5 0 "- климатическое исполнение по ГОСТ 15150 У2 (-40°С...+50°С)")
	(command "_text" "_ML" (list (+ x-pnt-ins 5) (- (- y-pnt-ins (* dlt-y 8)) 4)) 2.5 0 "- степень защиты IP54 по ГОСТ 14254-96")
	
			
	(command "_TEXT" "_MC" (list (+ x-pnt-ins 160) (- (- y-pnt-ins (* dlt-y 0)) 4)) 2.5 0 (strcat "ПЭМ-" str-0 str-6)) ;Тип, марка, обозначение документа, опросного листа

	(command "_text" "_MC" (list (+ x-pnt-ins 322.5) (- (- y-pnt-ins (* dlt-y 0)) 4)) 2.5 0 str-99)

	(repeat nmbr-ln
  	(command "_insert" "зс-пустая-строка" "_X" 1 "_Y" 1 "_Z" 1 "_R" 0 (list x-pnt-ins y-pnt-ins-1))
  	(setq y-pnt-ins-1 (- y-pnt-ins-1 8)
  	);setq
	);repeat
								
	(command "_text" "_MC" (list (+ x-pnt-ins 247.5) (- (- y-pnt-ins (* dlt-y 0)) 4)) 2.5 0 "ООО \"АБС ЗЭиМ")
	(command "_text" "_MC" (list (+ x-pnt-ins 247.5) (- (- y-pnt-ins (* dlt-y 1)) 4)) 2.5 0 "Автоматизация\",")
	(command "_text" "_MC" (list (+ x-pnt-ins 247.5) (- (- y-pnt-ins (* dlt-y 2)) 4)) 2.5 0 "г. Чебоксары")
			
	(command "_text" "_MC" (list (+ x-pnt-ins 280) (- (- y-pnt-ins (* dlt-y 0)) 4)) 2.5 0 "шт.")
	(setq cntr-1 (+ cntr-1 1)
	);setq
);repeat

(princ)
)
;;;;////////////////////////////////////////////////////////////////////////////////////////////////////////////////////////////////////////////////////////////////////////////
;;;;////////////////////////////////////////////////////////////////////////////////////////////////////////////////////////////////////////////////////////////////////////////
