;/////// ************************************************************ ///////////////////////////////////////////////////////////////////////////////////////////////////////////
;/////// штамп 55 мм                                                  ///////////////////////////////////////////////////////////////////////////////////////////////////////////

(defun 01-formats-spds-only-stamp-55mm

(block-name-55 / adoc pnt-1 pnt-txt31 pnt-txt32 txt-31 txt-32 xpnt-1 ypnt-1)

(vl-load-com)
(vla-startundomark (setq adoc (vla-get-activedocument (vlax-get-acad-object))));start undo

(setvar "cmdecho" 0)
(setvar "osmode" 6199)

(setq pnt-1 (getpoint "\nУкажите точку вставки\n")
			xpnt-1 (nth 0 pnt-1)
      ypnt-1 (nth 1 pnt-1)
      
      pnt-txt31 (list (- xpnt-1 27.5) (+ ypnt-1 20))
      pnt-txt32 (list (- xpnt-1 10) (+ ypnt-1 20))
);setq

(setvar "osmode" 0)

(command "_insert" block-name-55 "_X" 1 "_Y" 1 "_Z" 1 "_R" 0 pnt-1)

(setq txt-31
	(entmakex
		(list
			'(0 . "TEXT")
			'(100 . "AcDbEntity")
			'(100 . "AcDbText")
			(cons 10 pnt-txt31) ; нач точка текста
			(cons 11 pnt-txt31) ; нач точка текста
			'(1 . "***1") ; содержание текста
			'(40 . 3.5) ; высота текста
			'(41 . 1) ; растяжение текста
			'(50 . 0) ; поворот текста
			'(72 . 1) ; гориз выравнивание текста
			'(73 . 2) ; верт выравнивание текста
			'(370 . -1) ; толщина текста
			(cons 7 "Standard") ; стиль текста
		);list
	);entmakex
);setq

(setq txt-32
	(entmakex
		(list
			'(0 . "TEXT")
			'(100 . "AcDbEntity")
			'(100 . "AcDbText")
			(cons 10 pnt-txt32) ; нач точка текста
			(cons 11 pnt-txt32) ; нач точка текста
			'(1 . "***2") ; содержание текста
			'(40 . 3.5) ; высота текста
			'(41 . 1) ; растяжение текста
			'(50 . 0) ; поворот текста
			'(72 . 1) ; гориз выравнивание текста
			'(73 . 2) ; верт выравнивание текста
			'(370 . -1) ; толщина текста
			(cons 7 "Standard") ; стиль текста
		);list
	);entmakex
);setq

(command "_regenall")

(vla-endundomark adoc)	
(setvar "osmode" 6199)
(setvar "cmdecho" 1)
(princ)
)
;///////                                                              ///////////////////////////////////////////////////////////////////////////////////////////////////////////
;/////// ************************************************************ ///////////////////////////////////////////////////////////////////////////////////////////////////////////
