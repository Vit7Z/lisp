;/////// *************************************************************///////////////////////////////////////////////////////////////////////////////////////////////////////////////////////////////////////////////////////////////////////
;/////// штамп 40 мм, спдс                                            ///////////////////////////////////////////////////////////////////////////////////////////////////////////////////////////////////////////////////////////////////////
;/////// *************************************************************///////////////////////////////////////////////////////////////////////////////////////////////////////////////////////////////////////////////////////////////////////

(defun 01-formats-spds-stamp-40mm-okrch

( / adoc lin-1 lin-10 lin-11 lin-12 lin-13 lin-14 lin-15 lin-16 lin-17 lin-18 lin-19 lin-2 lin-20 lin-21 lin-22 lin-3 lin-4 lin-5 lin-6 lin-7 lin-8 lin-9 rctn-1 rctn-10 rctn-11 rctn-12 rctn-13 rctn-14 rctn-15 rctn-16 rctn-17 rctn-18 
rctn-19 rctn-2 rctn-20 rctn-21 rctn-22 rctn-23 rctn-24 rctn-25 rctn-3 rctn-4 rctn-5 rctn-6 rctn-7 rctn-8 rctn-9 txt-1 txt-11 txt-13 txt-14 txt-15 txt-16 txt-18 txt-19 txt-2 txt-20 txt-21 txt-22 txt-25 txt-26 txt-27 txt-28 txt-29 txt-3 
txt-4 txt-5 txt-6 txt-7 txt-8 txt-9)

(vl-load-com)
(vla-startundomark
  (setq adoc (vla-get-activedocument (vlax-get-acad-object)))
);start undo

(if (= (tblsearch "layer" "wspom") nil)
  (command "_layer" "Создать" "wspom" "Тип" "Continuous" "wspom" "Цвет" 3 "wspom" ""); создаем слой wspom
);if

(if (= (tblsearch "block" "штамп-40мм-спдс-1" ) nil)
	(progn				; если данного блока нет
		(setvar	"OSMODE" 0)
		(setvar	"CLAYER" "0")
		(setvar "CELWEIGHT" 60)
 		(command "_RECTANGLE" '(-185 40) '(-175 30))
		(setq rctn-1 (entlast))
 		(command "_RECTANGLE" '(-175 40) '(-165 30))
		(setq rctn-2 (entlast))	
		(command "_RECTANGLE" '(-165 40) '(-155 30))	
		(setq rctn-3 (entlast))
		(command "_RECTANGLE" '(-155 40) '(-145 30))
		(setq rctn-4 (entlast))
		(command "_RECTANGLE" '(-145 40) '(-130 30))
		(setq rctn-5 (entlast))
		(command "_RECTANGLE" '(-130 40) '(-120 30))
		(setq rctn-6 (entlast))
		(command "_RECTANGLE" '(-185 30) '(-175 25))
		(setq rctn-7 (entlast))
    (command "_RECTANGLE" '(-175 30) '(-165 25))
		(setq rctn-8 (entlast))
		(command "_RECTANGLE" '(-165 30) '(-155 25))
		(setq rctn-9 (entlast))
		(command "_RECTANGLE" '(-155 30) '(-145 25))
		(setq rctn-10 (entlast))
		(command "_RECTANGLE" '(-145 30) '(-130 25))
		(setq rctn-11 (entlast))
		(command "_RECTANGLE" '(-130 30) '(-120 25))
		(setq rctn-12 (entlast))
		(command "_RECTANGLE" '(-185 30) '(-165 0))
		(setq rctn-13 (entlast))
		(command "_RECTANGLE" '(-165 30) '(-145 0))
		(setq rctn-14 (entlast))
		(command "_RECTANGLE" '(-145 30) '(-130 0))
		(setq rctn-15 (entlast))
		(command "_RECTANGLE" '(-130 30) '(-120 0))
		(setq rctn-16 (entlast))
		(command "_RECTANGLE" '(-120 40) '(0 25))
		(setq rctn-17 (entlast))
 		(command "_RECTANGLE" '(-120 25) '(-50 0))
		(setq rctn-18 (entlast))	
		(command "_RECTANGLE" '(-50 25) '(-35 20))	
		(setq rctn-19 (entlast))
		(command "_RECTANGLE" '(-35 25) '(-20 20))	
		(setq rctn-20 (entlast))
		(command "_RECTANGLE" '(-20 25) '(0 20))
		(setq rctn-21 (entlast))
		(command "_RECTANGLE" '(-50 20) '(-35 15))
		(setq rctn-22 (entlast))
		(command "_RECTANGLE" '(-35 20) '(-20 15))
		(setq rctn-23 (entlast))
		(command "_RECTANGLE" '(-20 20) '(0 15))
		(setq rctn-24 (entlast))
        (command "_RECTANGLE" '(-50 15) '(0 0))
		(setq rctn-25 (entlast))
				
		(setvar "CELWEIGHT" -1)
		(command "_.line" '(-185 35) '(-175 35) "")
		(setq lin-1 (entlast))
		(command "_.line" '(-175 35) '(-165 35) "")
		(setq lin-2 (entlast))
		(command "_.line" '(-165 35) '(-155 35) "")
		(setq lin-3 (entlast))
		(command "_.line" '(-155 35) '(-145 35) "")
		(setq lin-4 (entlast))
		(command "_.line" '(-145 35) '(-130 35) "")
		(setq lin-5 (entlast))
		(command "_.line" '(-130 35) '(-120 35) "")
		(setq lin-6 (entlast))
		
		(command "_.line" '(-185 20) '(-165 20) "")
		(setq lin-7 (entlast))
		(command "_.line" '(-165 20) '(-145 20) "")
		(setq lin-8 (entlast))
		(command "_.line" '(-145 20) '(-130 20) "")
		(setq lin-9 (entlast))
		(command "_.line" '(-130 20) '(-120 20) "")
		(setq lin-10 (entlast))
		(command "_.line" '(-185 15) '(-165 15) "")
		(setq lin-11 (entlast))
		(command "_.line" '(-165 15) '(-145 15) "")
		(setq lin-12 (entlast))
		(command "_.line" '(-145 15) '(-130 15) "")
		(setq lin-13 (entlast))
		(command "_.line" '(-130 15) '(-120 15) "")
		(setq lin-14 (entlast))
		(command "_.line" '(-185 10) '(-165 10) "")
		(setq lin-15 (entlast))
		(command "_.line" '(-165 10) '(-145 10) "")
		(setq lin-16 (entlast))
		(command "_.line" '(-145 10) '(-130 10) "")
		(setq lin-17 (entlast))
		(command "_.line" '(-130 10) '(-120 10) "")
		(setq lin-18 (entlast))
		(command "_.line" '(-185 5) '(-165 5) "")
		(setq lin-19 (entlast))
		(command "_.line" '(-165 5) '(-145 5) "")
		(setq lin-20 (entlast))
		(command "_.line" '(-145 5) '(-130 5) "")
		(setq lin-21 (entlast))
		(command "_.line" '(-130 5) '(-120 5) "")
		(setq lin-22 (entlast))
						
(setq txt-1
  (entmakex
    (list
      '(0 . "TEXT")
      '(100 . "AcDbEntity")
      '(100 . "AcDbText")
      '(10 -180. 27.5) ; нач точка текста
      '(11 -180. 27.5) ; нач точка текста
      '(1 . "Изм.") ; содержание текста
      '(40 . 2.5) ; высота текста
      '(41 . 0.8) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq
		
(setq txt-2 
  (entmakex
    (list
      '(0 . "TEXT")
      '(100 . "AcDbEntity")
      '(100 . "AcDbText")
      '(10 -170 27.5) ; нач точка текста
      '(11 -170 27.5) ; нач точка текста
      '(1 . "Кол.уч.") ; содержание текста
      '(40 . 2.5) ; высота текста
      '(41 . 0.8) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-3 
  (entmakex
    (list
      '(0 . "TEXT")
      '(100 . "AcDbEntity")
      '(100 . "AcDbText")
      '(10 -160 27.5) ; нач точка текста
      '(11 -160 27.5) ; нач точка текста
      '(1 . "Лист") ; содержание текста
      '(40 . 2.5) ; высота текста
      '(41 . 0.8) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-4 
  (entmakex
    (list
      '(0 . "TEXT")
      '(100 . "AcDbEntity")
      '(100 . "AcDbText")
      '(10 -150 27.5) ; нач точка текста
      '(11 -150 27.5) ; нач точка текста
      '(1 . "№ док.") ; содержание текста
      '(40 . 2.5) ; высота текста
      '(41 . 0.8) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq	
		
(setq txt-5 
  (entmakex
    (list
      '(0 . "TEXT")
      '(100 . "AcDbEntity")
      '(100 . "AcDbText")
      '(10 -137.5 27.5) ; нач точка текста
      '(11 -137.5 27.5) ; нач точка текста
      '(1 . "Подпись") ; содержание текста
      '(40 . 2.5) ; высота текста
      '(41 . 0.8) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-6 
  (entmakex
    (list
      '(0 . "TEXT")
      '(100 . "AcDbEntity")
      '(100 . "AcDbText")
      '(10 -125 27.5) ; нач точка текста
      '(11 -125 27.5) ; нач точка текста
      '(1 . "Дата") ; содержание текста
      '(40 . 2.5) ; высота текста
      '(41 . 0.8) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-7 
  (entmakex
    (list
      '(0 . "TEXT")
      '(100 . "AcDbEntity")
      '(100 . "AcDbText")
      '(10 -184.5 22.5) ; нач точка текста
      '(11 -184.5 22.5) ; нач точка текста
      '(1 . "Инженер") ; содержание текста
      '(40 . 2.5) ; высота текста
      '(41 . 1) ; растяжение текста
      '(50 . 0) ; поворот текста
      '(72 . 0) ; гориз выравнивание текста
      '(73 . 2) ; верт выравнивание текста
      '(370 . -1) ; толщина текста
       (cons 7 (getvar "textstyle")) ; стиль текста
    ) ; end of list
  ); entmakex
); setq	

(setq txt-8
  (entmakex
    (list
      '(0 . "TEXT")
      '(100 . "AcDbEntity")
      '(100 . "AcDbText")
      '(10 -184.5 17.5) ; нач точка текста
      '(11 -184.5 17.5) ; нач точка текста
      '(1 . "Нач. отдела") ; содержание текста
      '(40 . 2.5) ; высота текста
      '(41 . 1) ; растяжение текста
      '(50 . 0) ; поворот текста
      '(72 . 0) ; гориз выравнивание текста
      '(73 . 2) ; верт выравнивание текста
      '(370 . -1) ; толщина текста
       (cons 7 (getvar "textstyle")) ; стиль текста
    ) ; end of list
  ); entmakex
); setq

(setq txt-9
  (entmakex
    (list
      '(0 . "TEXT")
      '(100 . "AcDbEntity")
      '(100 . "AcDbText")
      '(10 -184.5 12.5) ; нач точка текста
      '(11 -184.5 12.5) ; нач точка текста
      '(1 . "ГИП") ; содержание текста
      '(40 . 2.5) ; высота текста
      '(41 . 1) ; растяжение текста
      '(50 . 0) ; поворот текста
      '(72 . 0) ; гориз выравнивание текста
      '(73 . 2) ; верт выравнивание текста
      '(370 . -1) ; толщина текста
       (cons 7 (getvar "textstyle")) ; стиль текста
    ) ; end of list
  ); entmakex
); setq

(setq txt-11
  (entmakex
    (list
      '(0 . "TEXT")
      '(100 . "AcDbEntity")
      '(100 . "AcDbText")
      '(10 -184.5 2.5) ; нач точка текста
      '(11 -184.5 2.5) ; нач точка текста
      '(1 . "Н. контр.") ; содержание текста
      '(40 . 2.5) ; высота текста
      '(41 . 1) ; растяжение текста
      '(50 . 0) ; поворот текста
      '(72 . 0) ; гориз выравнивание текста
      '(73 . 2) ; верт выравнивание текста
      '(370 . -1) ; толщина текста
       (cons 7 (getvar "textstyle")) ; стиль текста
    ) ; end of list
  ); entmakex
); setq

(setq txt-13
  (entmakex
    (list
      '(0 . "TEXT")
      '(100 . "AcDbEntity")
      '(100 . "AcDbText")
      '(10 -164.5 22.5) ; нач точка текста
      '(11 -164.5 22.5) ; нач точка текста
      '(1 . "*******") ; содержание текста
      '(40 . 2.5) ; высота текста
      '(41 . 0.8) ; растяжение текста
      '(50 . 0) ; поворот текста
      '(72 . 0) ; гориз выравнивание текста
      '(73 . 2) ; верт выравнивание текста
      '(370 . -1) ; толщина текста
       (cons 7 (getvar "textstyle")) ; стиль текста
    ) ; end of list
  ); entmakex
); setq

(setq txt-14
  (entmakex
    (list
      '(0 . "TEXT")
      '(100 . "AcDbEntity")
      '(100 . "AcDbText")
      '(10 -164.5 17.5) ; нач точка текста
      '(11 -164.5 17.5) ; нач точка текста
      '(1 . "*******") ; содержание текста
      '(40 . 2.5) ; высота текста
      '(41 . 1) ; растяжение текста
      '(50 . 0) ; поворот текста
      '(72 . 0) ; гориз выравнивание текста
      '(73 . 2) ; верт выравнивание текста
      '(370 . -1) ; толщина текста
       (cons 7 (getvar "textstyle")) ; стиль текста
    ) ; end of list
  ); entmakex
); setq

(setq txt-15
  (entmakex
    (list
      '(0 . "TEXT")
      '(100 . "AcDbEntity")
      '(100 . "AcDbText")
      '(10 -164.5 12.5) ; нач точка текста
      '(11 -164.5 12.5) ; нач точка текста
      '(1 . "*******") ; содержание текста
      '(40 . 2.5) ; высота текста
      '(41 . 1) ; растяжение текста
      '(50 . 0) ; поворот текста
      '(72 . 0) ; гориз выравнивание текста
      '(73 . 2) ; верт выравнивание текста
      '(370 . -1) ; толщина текста
       (cons 7 (getvar "textstyle")) ; стиль текста
    ) ; end of list
  ); entmakex
); setq

(setq txt-16
  (entmakex
    (list
      '(0 . "TEXT")
      '(100 . "AcDbEntity")
      '(100 . "AcDbText")
      '(10 -164.5 2.5) ; нач точка текста
      '(11 -164.5 2.5) ; нач точка текста
      '(1 . "*******") ; содержание текста
      '(40 . 2.5) ; высота текста
      '(41 . 1) ; растяжение текста
      '(50 . 0) ; поворот текста
      '(72 . 0) ; гориз выравнивание текста
      '(73 . 2) ; верт выравнивание текста
      '(370 . -1) ; толщина текста
       (cons 7 (getvar "textstyle")) ; стиль текста
    ) ; end of list
  ); entmakex
); setq

(setq txt-18
  (entmakex
    (list
      '(0 . "TEXT")
      '(100 . "AcDbEntity")
      '(100 . "AcDbText")
      '(10 -125 22.5) ; нач точка текста
      '(11 -125 22.5) ; нач точка текста
      '(1 . "дат1") ; содержание текста
      '(40 . 2.5) ; высота текста
      '(41 . 1) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-19
  (entmakex
    (list
      '(0 . "TEXT")
      '(100 . "AcDbEntity")
      '(100 . "AcDbText")
      '(10 -125 17.5) ; нач точка текста
      '(11 -125 17.5) ; нач точка текста
      '(1 . "дат1") ; содержание текста
      '(40 . 2.5) ; высота текста
      '(41 . 1) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-20
  (entmakex
    (list
      '(0 . "TEXT")
      '(100 . "AcDbEntity")
      '(100 . "AcDbText")
      '(10 -125 12.5) ; нач точка текста
      '(11 -125 12.5) ; нач точка текста
      '(1 . "дат1") ; содержание текста
      '(40 . 2.5) ; высота текста
      '(41 . 1) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-21
  (entmakex
    (list
      '(0 . "TEXT")
      '(100 . "AcDbEntity")
      '(100 . "AcDbText")
      '(10 -125 2.5) ; нач точка текста
      '(11 -125 2.5) ; нач точка текста
      '(1 . "дат1") ; содержание текста
      '(40 . 2.5) ; высота текста
      '(41 . 1) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq


(setq txt-22
  (entmakex
    (list
      '(0 . "TEXT")
      '(100 . "AcDbEntity")
      '(100 . "AcDbText")
      '(10 -60. 32.5) ; нач точка текста
      '(11 -60. 32.5) ; нач точка текста
      '(1 . "*******-АТХ") ; содержание текста
      '(40 . 3.5) ; высота текста
      '(41 . 1) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq


(setq txt-25
  (entmakex
    (list
      '(0 . "TEXT")
      '(100 . "AcDbEntity")
      '(100 . "AcDbText")
      '(10 -42.5 22.5) ; нач точка текста
      '(11 -42.5 22.5) ; нач точка текста
      '(1 . "Стадия") ; содержание текста
      '(40 . 2.5) ; высота текста
      '(41 . 1) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-26
  (entmakex
    (list
      '(0 . "TEXT")
      '(100 . "AcDbEntity")
      '(100 . "AcDbText")
      '(10 -27.5 22.5) ; нач точка текста
      '(11 -27.5 22.5) ; нач точка текста
      '(1 . "Лист") ; содержание текста
      '(40 . 2.5) ; высота текста
      '(41 . 1) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-27
  (entmakex
    (list
      '(0 . "TEXT")
      '(100 . "AcDbEntity")
      '(100 . "AcDbText")
      '(10 -10. 22.5) ; нач точка текста
      '(11 -10. 22.5) ; нач точка текста
      '(1 . "Листов") ; содержание текста
      '(40 . 2.5) ; высота текста
      '(41 . 1) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

(setq txt-28
  (entmakex
    (list
      '(0 . "MTEXT")
      '(100 . "AcDbEntity")
      '(100 . "AcDbMText")
      '(10 -25. 7.5) ; нач точка текста
      '(1 . "ООО \"*******\", \\P г. Москва") ; содержание текста
      '(40 . 3.5) ; высота текста
      '(41 . 50) ; растяжение текста
      '(42 . 50) ; ширина текста
      '(71 . 5) ; гориз выравнивание текста
      '(370 . -1) ; толщина текста
       (cons 7 (getvar "textstyle")) ; стиль текста
    ) ; end of list
  ); entmakex
); setq

(setq txt-29
  (entmakex
    (list
      '(0 . "TEXT")
      '(100 . "AcDbEntity")
      '(100 . "AcDbText")
      '(10 -42.5 17.5) ; нач точка текста
      '(11 -42.5 17.5) ; нач точка текста
      '(1 . "РД**") ; содержание текста
      '(40 . 3.5) ; высота текста
      '(41 . 1) ; растяжение текста
      '(50 . 0) ; поворот текста
      '(72 . 1) ; гориз выравнивание текста
      '(73 . 2) ; верт выравнивание текста
      '(370 . -1) ; толщина текста
       (cons 7 (getvar "textstyle")) ; стиль текста
    ) ; end of list
  ); entmakex
); setq

  (command "_block" "штамп-40мм-спдс-1" '(0 0) rctn-1 rctn-2 rctn-3 rctn-4 rctn-5 rctn-6 rctn-7 rctn-8 rctn-9 rctn-10 rctn-11 rctn-12 rctn-13 rctn-14 rctn-15 rctn-16 rctn-17 rctn-18 rctn-19 rctn-20 rctn-21 rctn-22 rctn-23 rctn-24 
  																						 rctn-25 
  																						 lin-1 lin-2 lin-3 lin-4 lin-5 lin-6 lin-7 lin-8 lin-9 lin-10 lin-11 lin-12 lin-13 lin-14 lin-15 lin-16 lin-17 lin-18 lin-19 lin-20 lin-21 lin-22 txt-1 
  																						 txt-2 txt-3 txt-4 txt-5 txt-6 txt-7 txt-8 txt-9 txt-11 txt-13 txt-14 txt-15 txt-16 txt-18 txt-19 txt-20 txt-21 txt-22 txt-25 txt-26 txt-27 txt-28 txt-29
		"")
  ); end progn
); end if

(vla-endundomark adoc)
(setvar	"ORTHOMODE" 1)
(setvar	"OSMODE" 6199)
(setvar "cmdecho" 1)
(princ)
)
;/////// конец программы /////////////////////////////////////////////////////////////////
