;/////// ************************************************************ //////////////////////////////////////////////////////////////////
;/////// очистка списка масштабов                                     //////////////////////////////////////////////////////////////////
;/////// ************************************************************ //////////////////////////////////////////////////////////////////

(defun restore-scale-list
  ()
  
  (setvar "cmdecho" 0)
  (command "_.-scalelistedit" "_r" "_y" "_e")
  
  (setvar "ACADLSPASDOC" 1)
  
  (setvar "cmdecho" 1)
);defun 
(princ"\n")
(restore-scale-list)
(princ"\n")
(princ)
;/////// конец ///////
