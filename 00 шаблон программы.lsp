;/////// *************************************************************//////////////////////////////////////////////////////////////////////
;/////// название программы****************                           //////////////////////////////////////////////////////////////////////
;/////// *************************************************************//////////////////////////////////////////////////////////////////////
(defun c:**************

( / ***********)

(vl-load-com)
(vla-startundomark (setq adoc (vla-get-activedocument (vlax-get-acad-object))));start undo

(setvar "cmdecho" 0)


(setvar "osmode" 6199)
(setvar "cmdecho" 1)
(vla-endundomark adoc)
(princ)
)


(1000-delete-items-le nmbr-ln x-pnt-ins y-pnt-ins);удаление предыдущей записи

(1000-delete-items-spcf nmbr-ln x-pnt-ins y-pnt-ins);удаление предыдущей записи

(1000-delete-items-spcf-crtf nmbr-ln x-pnt-ins y-pnt-ins);удаление предыдущего сертификата

(1000-delete-items-le-cgv nmbr-ln x-pnt-ins y-pnt-ins);удаление предыдущей записи

mln- - метка строки меню



;/////// *************************************************************//////////////////////////////////////////////////////////////////////
;/////// КОНЕЦ ПРОГРАММЫ                                              //////////////////////////////////////////////////////////////////////
;/////// *************************************************************//////////////////////////////////////////////////////////////////////

;//////////////////////////////////////////////////////       ПЭ

(split-str-parts-le-01-general str-701 str-702 pnt-ins "**1**");













;//////////////////////////////////////////////////////      спецификация

	(setq str-701 "Блок вентильный"
	
				str-702 (list (cons 1 (strcat "кол. вентилей " str-02))
											(cons 2 (strcat "дренаж " str-05))
											(cons 3 (strcat "к процессу " str-03))
											(cons 4 (strcat "к прибору " str-04))
								);list
											
				str-manufact "ОВЕН, г. Москва"
				
				str-order (list (cons 1 str-01) 
												(cons 2 "-") 
												(cons 3 nil) ;;;  здесь обозначение ТУ или НТД
									);list
				
				str-unit "шт."
				str-note nil ;;;;;;; примечание, текстовая строка
	);setq
	
	(split-str-parts-spcf-01-general str-701 str-702 str-order str-manufact str-unit str-99 str-note pnt-ins);
	


;//////////////////////////////////////////////////////      общий вид шкафа
	(setq str-701 (strcat "Выключатель автоматический, " str-01-1 ", " str-02 ", Iном. " str-03 "А, " str-01-2 ", артикул " str-04));setq
			
	(split-str-parts-lecgv-01-general str-701 str-702 str-703 str-99 pnt-ins);
	
	;str-702 обозначение (ГОСТ, Ту) - для труб, материалов
	;str-703 примечание
	
;//////////////////////////////////////////////////////      коец фрагмента	
	

;//////////////////////////////////////////////////////      обработка кнопки удаить в диалоге


(set_tile "ptxt-41" (nth 0 list-900-menu))
(set_tile "ptxt-42" (nth 1 list-900-menu))

(set_tile "ptxt-51" (nth 2 list-900-menu))
(set_tile "ptxt-52" (nth 3 list-900-menu))

(set_tile "ptxt-61" (nth 4 list-900-menu))
(set_tile "ptxt-62" (nth 5 list-900-menu))

(setq list-02 list-01-read-file
			list-03 list-02-read-file
			list-04 list-03-read-file
			list-05 list-04-read-file
			list-06 list-05-read-file
			list-99 list-06-read-file
			list-900 list-900-dscr
);setq

;//////////////////////////////////////////////////////      коец фрагмента


;//////////////////////////////////////////////////////     кусок программы, чтобы был правильный порядок в списках
(if (/= list-901 nil) 
	(setq list-901 (reverse list-901)
				list-902 (reverse list-902)
	);setq
);if

====================== тело программы =======================================

(setq list-902 (vl-list* tmp-902 list-902)
			list-902 (reverse list-902)
			list-901 (reverse list-901)
);setq

;//////////////////////////////////////////////////////      коец фрагмента


;///////                                                              //////////////////////////////////////////////////////////////////////
(defun 01-spds-stamp-55mm-spcf-create-rectangle

(sign-close num-side layer pnt-1 pnt-2 pnt-3 pnt-4 sign-thik /)
    
(setq rectangle-tmp
  (entmakex
    (list
      '(0 . "LWPOLYLINE")
      '(100 . "AcDbEntity")
      '(100 . "AcDbPolyline")
      (cons 70 sign-close) ;замкнутость
      (cons 90 num-side) ;числ сторон
      '(43 . 0.0)
      (cons 8 layer);слой
      (cons 10  pnt-1);точки вершин
      (cons 10  pnt-2)
      (cons 10  pnt-3)
      (cons 10  pnt-4)
      (cons 10  pnt-1)
      (cons 370 sign-thik);толщина линии
    );list
  );entmakex
);setq


(princ)
(gc)
)
;///////////////////////////////////////////////////////////////////////////////////////////////////////////////////////////////////////////
;///////////////////////////////////////////////////////////////////////////////////////////////////////////////////////////////////////////


;/////// ************************************************************ //////////////////////////////////////////////////////////////////////
;/////// извлекаем данные из объекта для штампа                       //////////////////////////////////////////////////////////////////////
;/////// ************************************************************ //////////////////////////////////////////////////////////////////////
(defun 101-00-spcf-pages-take-data-stamp

(data-obj / type-obj)

(if (/= data-obj nil)
	(progn
		(setq data-obj (entget (ssname data-obj 0))
		      type-obj (cdr (assoc 0 data-obj))
		);setq
  
  	(if (= type-obj "TEXT")
  		(setq data-txt (list (assoc 0 data-obj) (assoc 40 data-obj) (assoc 41 data-obj) (assoc 1 data-obj)));setq
  	);if
  
  	(if (= type-obj "MTEXT")
  		(setq data-txt (list (assoc 0 data-obj) (assoc 40 data-obj) (assoc 41 data-obj) (assoc 1 data-obj)));setq
  	);if

	);progn 
);if

(if (= data-obj nil) (setq data-txt nil))

)

;///////                                                              //////////////////////////////////////////////////////////////////////
;/////// ************************************************************ //////////////////////////////////////////////////////////////////////
