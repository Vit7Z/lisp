;/////// ************************************************************ //////////////////////////////////////////////////////////////////
;/////// перфоизделия в СО                                            //////////////////////////////////////////////////////////////////
;/////// ************************************************************ //////////////////////////////////////////////////////////////////
(defun 101-08-punched

( / adoc dcl-id list-01 list-02 list-99 str-01 type-list)

(vl-load-com)
(vla-startundomark (setq adoc (vla-get-activedocument (vlax-get-acad-object))));start undo

(setq list-01 (list "Швеллер перфорированный" 
      							"Уголок перфорированный" 
      							"Полоса перфорированная")
      list-901 nil
      list-902 nil
      
			str-01 nil
);setq

(txt-01-101-08-punched)

(if (< (setq dcl-id (load_dialog "dia-101-08-punched.dcl")) 0) ;ищем диалог
		(progn
			(alert "Не найден dcl-файл")
			(exit)
		);progn
);if

(if (not (new_dialog "dia_101_08_punched" dcl-id))
		(exit)
);if

(list-filling "txt-01" list-01)
(list-filling "txt-02" list-02)
(list-filling "txt-99" list-99)

(set_tile "txt-01" "0")
(set_tile "txt-02" "0")
(set_tile "txt-99" "0")

(action_tile "txt-01"
  (strcat "(txt-01-101-08-punched)");strcat
);action_tile

(action_tile "txt-02"
  (strcat "(set_tile \"txt-99\" $value)");srcat
);action_tile

(action_tile "but1"
  (strcat "(but1-101-08-punched)");strcat
);action_tile

(action_tile "but2"
  (strcat "(setq type-list \"le\")"
          "(done_dialog)"
  );strcat
);action_tile

(action_tile "but3"
  (strcat "(setq type-list \"spcf\")"
          "(done_dialog)"
  );strcat
);action_tile

(action_tile "but4"
  (strcat "(setq type-list \"lecgv\")"
          "(done_dialog)"
  );strcat
);action_tile

(action_tile "accept"
  (strcat "(done_dialog)"
          "(exit)"
  );strcat
);action_tile

(start_dialog)
(unload_dialog dcl-id)

(cond
	((= type-list "le") (le-101-08-punched));=
	((= type-list "spcf") (spcf-101-08-punched));=
	((= type-list "lecgv") (lecgv-101-08-punched));=
);if

(setvar "osmode" 6199)
(setvar "cmdecho" 1)
(vla-endundomark adoc)
(princ)
)
;/////// ************************************************************ ///////////////////////////////////////////////////////////////////////////////////////////////////////////
;/////// конец программы                                             ////////////////////////////////////////////////////////////////////////////////////////////////////////////
;/////// ************************************************************ ///////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun txt-01-101-08-punched

(/)

(if (= nil str-01) 
	(setq str-01 (nth 0 list-01))
	(setq str-01 (nth (atoi (get_tile "txt-01")) list-01))
);if

(if (= "Швеллер перфорированный" str-01)
  (progn
		(setq list-02 (list "ШП 32х16х2000" "ШП 60х35х2000")
					list-99 (list "1,6" "3,1")
		);setq
		(set_tile "ptxt-022" "(ШхВхД, мм)")
  );progn
);if

(if (= "Уголок перфорированный" str-01)
  (progn
		(setq list-02 (list "УП 35х25х2000" "УП 35х35х2000" "УП 42х25х2000" "УП 60х40х2000" "УП 60х60х2000")
					list-99 (list "1,3" "1,5" "1,3" "2,7" "3,1")
		);setq
		(set_tile "ptxt-022" "(ШхВхД, мм)")
  );progn
);if

(if (= "Полоса перфорированная" str-01)
  (progn
     (setq list-02 (list "ПП 20х2000" "ПП 30х2000" "ПП 40х2000" "ПП 130х2000" "ПП 190х2000" "ПП 270х2000")
     			 list-99 (list "2,2" "2,6" "3,0" "3,1" "3,3" "3,7")
     );setq
		(set_tile "ptxt-022" "(ШхД, мм)")
  );progn
);if

(list-filling "txt-02" list-02)
(list-filling "txt-99" list-99)

(set_tile "txt-02" "0")
(set_tile "txt-99" "0")

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun but1-101-08-punched

( / str-01 str-02 str-902 str-99 swtch)

(setq str-01 (nth (atoi (get_tile "txt-01")) list-01)
			str-02 (nth (atoi (get_tile "txt-02")) list-02)
			str-99 (nth (atoi (get_tile "txt-99")) list-99)
      swtch list-901
);setq

(if (/= swtch nil) (setq list-902 (reverse list-902)));if

(setq list-901 (vl-list* (strcat str-01 "  " str-02) list-901));setq

(setq str-902 (list (cons 1 str-01) (cons 2 str-02) (cons 99 str-99))
			list-902 (vl-list* str-902 list-902)
);setq

(setq list-902 (reverse list-902));setq

(list-filling "txt-901" (reverse list-901))

(princ)
)
;;;;/////////////////////////////////////////////////////////////////////////////////////////////////////////////////////////////////////////////////////////////////////////////
;;;;/////////////////////////////////////////////////////////////////////////////////////////////////////////////////////////////////////////////////////////////////////////////

;/////// ************************************************************ ///////////////////////////////////////////////////////////////////////////////////////////////////////////
;/////// вывод в ПЭ                                                   ///////////////////////////////////////////////////////////////////////////////////////////////////////////
(defun le-101-08-punched

( / cntr-1 pnt-ins str-01 str-02 str-702 str-tmp str-txt)

(setq cntr-1 0);setq

(setvar "textstyle" "Standard")

(repeat (length list-902)
	(setq str-tmp (nth cntr-1 list-902)
				str-01 (cdr (assoc 1 str-tmp))
				str-02 (cdr (assoc 2 str-tmp))
				str-702 nil
	);setq

	(setvar "osmode" 6199)
	
	(setq pnt-ins		(getpoint "\nУкажите точку вставки\n"));setq

	(if (or (= str-01 "Швеллер перфорированный")
					(= str-01 "Уголок перфорированный"));
		(setq str-txt (strcat str-01 " " str-02 " (ШхВхД, мм)"))		
	);if

	(if (= str-01 "Полоса перфорированная")
		(setq str-txt (strcat str-01 " " str-02 " (ШхД, мм)"))		
	);if
	
	(split-str-parts-le-01-general str-txt str-702 pnt-ins "**1**");
	
	(setq cntr-1 (1+ cntr-1));setq
);repeat

(princ)
)
;;;;/////////////////////////////////////////////////////////////////////////////////////////////////////////////////////////////////////////////////////////////////////////////
;;;;/////////////////////////////////////////////////////////////////////////////////////////////////////////////////////////////////////////////////////////////////////////////


;;;;////////////////////////////////////////////////////////////////////////////////////////////////////////////////////////////////////////////////////////////////////////////
;;;;подпрограмма вывода в спцф                   ///////////////////////////////////////////////////////////////////////////////////////////////////////////////////////////////
(defun spcf-101-08-punched

( / cntr-1 pnt-ins str-01 str-02 str-022 str-701 str-702 str-702-01 str-99 str-crtf str-manufact str-order str-tmp str-unit)

(setq cntr-1 0);setq

(repeat (length list-902)
	(setq str-tmp (nth cntr-1 list-902)
				str-01 (cdr (assoc 1 str-tmp))
				str-02 (cdr (assoc 2 str-tmp))
				str-99 (cdr (assoc 99 str-tmp))
	);setq
	
	(setvar "osmode" 6199)
	
	(setq pnt-ins (getpoint "\nУкажите точку вставки\n")
				str-022 (substr str-02 4)
	);setq


	;/////////////////////////////////////////////////////////////////////////////////////////////////
	(cond 
		((or (= str-01 "Швеллер перфорированный") (= str-01 "Уголок перфорированный"));
			(setq str-702-01 (strcat "размеры (ШхВхД) " str-022 "мм"))
		);=
	
		((= str-01 "Полоса перфорированная")
			(setq str-702-01 (strcat "размеры (ШхД) " str-022 "мм"))
		);=
	);cond
	
	(setq str-701 str-01	
				str-702 (list (cons 1 str-702-01));list
				str-order (list (cons 1 str-02) 
												(cons 2 " ") 
												(cons 3 "ТУ36.22.21.00.021-91"));list
				str-manufact "ООО \"ЗЭМИ\", г. Москва"				
				str-unit "шт."				
				str-crtf nil
	);setq
	
	(split-str-parts-spcf-01-general str-701 str-702 str-order str-manufact str-unit str-99 str-crtf pnt-ins);	
 
	(setq cntr-1 (+ cntr-1 1));setq
);repeat

(princ)
)
;;;;/////////////////////////////////////////////////////////////////////////////////////////////////////////////////////////////////////////////////////////////////////////////
;;;;/////////////////////////////////////////////////////////////////////////////////////////////////////////////////////////////////////////////////////////////////////////////


;/////// ************************************************************ ///////////////////////////////////////////////////////////////////////////////////////////////////////////
;/////// вывод в ПЭ чро                                               ///////////////////////////////////////////////////////////////////////////////////////////////////////////
(defun lecgv-101-08-punched

( / cntr-1 dlt-y pnt-ins str-01 str-02 str-701 str-702 str-703 str-99 str-tmp str-txt x-pnt-ins y-pnt-ins)

(setq cntr-1 0
			str-703 nil
);setq

(setvar "textstyle" "Standard")

(repeat (length list-902)
	(setq str-tmp (nth cntr-1 list-902)
				str-01 (cdr (assoc 1 str-tmp))
				str-02 (cdr (assoc 2 str-tmp))
				str-99 (cdr (assoc 99 str-tmp))
	);setq

	(setvar "osmode" 6199)
	
	(setq pnt-ins (getpoint "\nУкажите точку вставки\n"));setq
	
	;;;;;;;;;///////////////////////////////////////////////////////////////////////////////
	(if (or (= str-01 "Швеллер перфорированный") (= str-01 "Уголок перфорированный"));
		(setq str-701 (strcat str-01 " " str-02 " (ШхВхД, мм)")
					
					str-702 "ТУ36.22.21.00.021-91"
		);setq
	);if

	(if (= str-01 "Полоса перфорированная")
		(setq str-txt (strcat str-01 " " str-02 " (ШхД, мм)"))		
	);if
	
	(split-str-parts-lecgv-01-general str-701 str-702 str-703 str-99 pnt-ins);
		
	(setq cntr-1 (1+ cntr-1));setq
);repeat

(princ)
)
;;;;/////////////////////////////////////////////////////////////////////////////////////////////////////////////////////////////////////////////////////////////////////////////
;;;;/////////////////////////////////////////////////////////////////////////////////////////////////////////////////////////////////////////////////////////////////////////////
