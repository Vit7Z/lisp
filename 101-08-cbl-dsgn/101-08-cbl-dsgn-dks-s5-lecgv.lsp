;;;;/////////////////////////////////////////////////////////////////////////////////////////////////////////////////////////////////////////////////////////////////////////////
;;;;подпрограмма вывода в ПЭ ЧРО               //////////////////////////////////////////////////////////////////////////////////////////////////////////////////////////////////
(defun 101-08-cbl-dsgn-dks-s5-lecgv

(list-902 / cntr-1 pnt-ins str-01 str-02 str-03 str-04 str-41 str-701 str-702 str-703 str-99 str-tmp)

(setq cntr-1 0);setq

(repeat (length list-902)
  (setvar "osmode" 6199)

	(setq str-tmp (nth cntr-1 list-902)
				str-01 (cdr (assoc 1 str-tmp))
				str-02 (cdr (assoc 2 str-tmp))
				str-03 (cdr (assoc 3 str-tmp))
				str-99 (cdr (assoc 99 str-tmp))
				
				str-701 nil
				str-702 nil
				str-703 nil
				pnt-ins (getpoint "\nУкажите точку вставки\n")
	);setq
	
	;;;;;;;;//////////////////////////////////////////////////////////////////////////////////////////
	(if (or (= "Лоток перфорированный" str-01) 
					(= "Крышка лотка" str-01))
					
		(setq str-04 (cdr (assoc 4 str-tmp))						
					str-701 (strcat str-01 " " str-02 ", код заказа " str-03 ", " str-04)					
					str-703 "Кол. в компл."
		);setq
	);if
	
	;;;;;;;;//////////////////////////////////////////////////////////////////////////////////////////
	(if (wcmatch str-01 "Угол*")
		(setq str-04 (cdr (assoc 4 str-tmp))						
					str-701 (strcat str-01 ", размеры " str-02 ", код заказа " str-03 ", " str-04)					
					str-703 "Кол. в компл."
		);setq
	);if
		
	;;;;;;;;//////////////////////////////////////////////////////////////////////////////////////////
	(if (wcmatch str-01 "Крышка для*")
		(setq str-701 (strcat str-01 ", " str-02 ", код заказа " str-03));setq
	);if
	
	;;;;;;;;//////////////////////////////////////////////////////////////////////////////////////////
	(if (wcmatch str-01 "Консоль*")
		(setq str-41 (cdr (assoc 41 str-tmp))
		      str-701 (strcat str-01 " " str-02 " " str-41 ", код заказа " str-03));setq
	);if

	;;;;;;;;//////////////////////////////////////////////////////////////////////////////////////////
	(if (or (wcmatch str-01 "Ответвитель*")
					(wcmatch str-01 "Соединитель*")
			);or
		(setq str-701 (strcat str-01 ", размеры " str-02 ", код заказа " str-03)
					str-703 "Кол. в компл."
		);setq
	);if
	
	;;;;;;;;//////////////////////////////////////////////////////////////////////////////////////////
	(if (wcmatch str-01 "Переходник*")
		(setq str-701 (strcat str-01 ", размеры " str-02 ", код заказа " str-03)
					str-703 "Кол. в компл."
		);setq
	);if
	
	;;;;;;;;//////////////////////////////////////////////////////////////////////////////////////////
	(if (wcmatch str-01 "Крепление к*")
		(setq str-701 (strcat str-01 " " str-02 ", код заказа " str-03));setq
	);if
	
	;;;;;;;;//////////////////////////////////////////////////////////////////////////////////////////
	(if (wcmatch str-01 "Профиль*")
		(setq str-04 (cdr (assoc 4 str-tmp))
		      str-701 (strcat str-01 " " str-02 ", " str-03 ", код заказа " str-04)
		);setq
	);if
	
	;;;;;;;///////////////////////////////////////////////////////////////
  (if (= str-01 "Перегородка SEP")
	  (setq str-701 (strcat str-01 ", размеры " str-02 ", код заказа " str-03));setq
  );if
	

	(if (/= str-701 nil)
		(split-str-parts-lecgv-01-general str-701 str-702 str-703 str-99 pnt-ins);
	);if
	
	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////
