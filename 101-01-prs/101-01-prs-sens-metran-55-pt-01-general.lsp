;/////// ************************************************************ //////////////////////////////////////////////////////////////////
;///////                                                              //////////////////////////////////////////////////////////////////
;/////// ************************************************************ //////////////////////////////////////////////////////////////////
(defun 101-01-prs-sens-metran-55-pt-01-general

( / adoc counter dcl-id list-02 list-03 list-04 list-05 list-06 list-07 list-08 list-09 list-10 list-11 list-901 list-902 str-02 str-f type-list)

(vl-load-com)
(vla-startundomark (setq adoc (vla-get-activedocument (vlax-get-acad-object))));start undo

(setq str-f 1
      counter 0
      str-02 nil
      list-02 (list "Метран-55-ДА" 
										"Метран-55-Ех-ДА" 
										"Метран-55-Вн-ДА" 
										"Метран-55-ДИ" 
										"Метран-55-Ех-ДИ" 
										"Метран-55-Вн-ДИ" 
										"Метран-55-ДВ" 
										"Метран-55-Ех-ДВ" 
										"Метран-55-Вн-ДВ" 
										"Метран-55-ДИВ" 
										"Метран-55-Ех-ДИВ" 
										"Метран-55-Вн-ДИВ")
      list-901 nil
      list-902 nil
);setq

(tmp-strt-101-metran-55)

(if (< (setq dcl-id (load_dialog "dia-101-01-prs-sens-metran-55-pt-01-general.dcl")) 0) ;ищем диалог
		(progn
			(alert "Не найден dcl-файл")
			(exit)
		);progn
);if

(if (not (new_dialog "dia_metran_55" dcl-id))
		(exit)
);if
 
(list-filling "txt-02" list-02)
(list-filling "txt-03" list-03)
(list-filling "txt-04" list-04)
(list-filling "txt-05" list-05)
(list-filling "txt-06" list-06)
(list-filling "txt-07" list-07)
(list-filling "txt-08" list-08)
(list-filling "txt-09" list-09)
(list-filling "txt-10" list-10)
(list-filling "txt-11" list-11)

(set_tile "txt-02" "0")
(set_tile "txt-03" "0")
(set_tile "txt-04" "0")
(set_tile "txt-05" "0")
(set_tile "txt-06" "0")
(set_tile "txt-07" "0")
(set_tile "txt-08" "0")
(set_tile "txt-09" "0")
(set_tile "txt-10" "0")
(set_tile "txt-11" "0")

(action_tile "txt-02"
  (strcat "(txt-02-101-metran-55)"
  				"(tmp-1-101-metran-55)"
  );strcat
);action_tile

(action_tile "txt-03"
  (strcat "(txt-03-101-metran-55)"
  				"(txt-04-101-metran-55)"
  );strcat
);action_tile

(action_tile "txt-04"
  (strcat "(txt-04-101-metran-55)"
  );strcat
);action_tile

(action_tile "txt-05"
  (strcat "(txt-05-101-metran-55)"
  				"(tmp-1-101-metran-55)"
  );strcat
);action_tile

(action_tile "but1"
  (strcat "(tmp-filling-fields-101-metran-55)"
  );strcat
);action_tile

(action_tile "but2"
  (strcat "(setq type-list \"le\")"
          "(done_dialog)"
  );strcat
);action_tile

(action_tile "but3"
  (strcat "(setq type-list \"spcf\")"
          "(done_dialog)"
  );strcat
);action_tile

(action_tile "accept"
  (strcat "(done_dialog)"
          "(exit)"
  );strcat
);action_tile

(start_dialog)
(unload_dialog dcl-id)

(if (= type-list "le") (tmp-le-101-metran-55));if
(if (= type-list "spcf") (tmp-spcf-101-metran-55));if
(if (= type-list "lecgv") (tmp-lecgv-101-metran-55));if


(setvar "osmode" 6199)
(setvar "cmdecho" 1)
(vla-endundomark adoc)
(princ)
)
;/////// конец программы ///////

;;;;/////////////////////////////////////////////////////////////////////////////////////////////////////////////////////////////////////////////////////////////////////////////
;;;;/////////////////////////////////////////////////////////////////////////////////////////////////////////////////////////////////////////////////////////////////////////////
(defun tmp-strt-101-metran-55

( / )

(if (= nil str-02) 
	(setq str-02 (nth 0 list-02));setq
	(setq str-02 (nth (atoi (get_tile "txt-02")) list-02));setq
);if

(if (= "Метран-55-ДА" str-02)
	(progn
		(setq list-03 (list "505" "506")
      		list-04 (list "0,25" "0,4" "0,6" "1,0" "1,6" "2,5")
      		list-05 (list "МП")
      		list-06 (list "Нет" "Да")
      		list-07 (list "УХЛ 3.1 (+5...+50)" "Т3 (-25...+70)" "У2 (-40...+70)")
      		list-08 (list "0,5" "0,25" "0,15")
      		list-09 (list "4-20" "0-5")
      		list-10 (list "С" "С2" "ШР")
      		list-11 (list "М20" "М20-Кр" "М12" "М12-Кр")
		);setq
	);progn
);if

(list-filling "txt-03" list-03)
(list-filling "txt-04" list-04)
(list-filling "txt-05" list-05)
(list-filling "txt-06" list-06)
(list-filling "txt-07" list-07)
(list-filling "txt-08" list-08)
(list-filling "txt-09" list-09)
(list-filling "txt-10" list-10)
(list-filling "txt-11" list-11)

(set_tile "txt-03" "0")
(set_tile "txt-04" "0")
(set_tile "txt-05" "0")
(set_tile "txt-06" "0")
(set_tile "txt-07" "0")
(set_tile "txt-08" "0")
(set_tile "txt-09" "0")
(set_tile "txt-10" "0")
(set_tile "txt-11" "0")

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun txt-02-101-metran-55

( / str-02)

(setq str-02 (nth (atoi (get_tile "txt-02")) list-02)
);setq

(if (= "Метран-55-ДА" str-02)
	(progn
		(setq list-03 (list "505" "506")
      		list-04 (list "0,25" "0,4" "0,6" "1,0" "1,6" "2,5")
      		list-05 (list "МП")
      		list-06 (list "Нет" "Да")
      		list-10 (list "С" "С2" "ШР")
		);setq
	);progn
);if

(if (= "Метран-55-Ех-ДА" str-02)
	(progn
		(setq list-03 (list "505" "506")
      		list-04 (list "0,25" "0,4" "0,6" "1,0" "1,6" "2,5")
      		list-05 (list "МП")
      		list-06 (list "Нет" "Да")
      		list-10 (list "С" "С2" "ШР")
		);setq
	);progn
);if

(if (= "Метран-55-Вн-ДА" str-02)
	(progn
		(setq list-03 (list "505" "506")
      		list-04 (list "0,25" "0,4" "0,6" "1,0" "1,6" "2,5")
      		list-05 (list "МП")
      		list-06 (list "Нет" "Да")
      		list-10 (list "С")
		);setq
	);progn
);if

(if (= "Метран-55-ДИ" str-02)
	(progn
		(setq list-03 (list "515" "516" "517" "518")
      		list-04 (list "0,25" "0,4" "0,6" "1,0" "1,6" "2,5")
      		list-05 (list "МП")
					list-06 (list "Нет" "Да")
					list-10 (list "С" "С2" "ШР")
		);setq
	);progn
);if

(if (= "Метран-55-Ех-ДИ" str-02)
	(progn
		(setq list-03 (list "515" "516" "517" "518")
      		list-04 (list "0,25" "0,4" "0,6" "1,0" "1,6" "2,5")
					list-06 (list "Нет" "Да")
					list-05 (list "МП")
					list-10 (list "С" "С2" "ШР")
		);setq
	);progn
);if

(if (= "Метран-55-Вн-ДИ" str-02)
	(progn
		(setq list-03 (list "515" "516" "517" "518")
      		list-04 (list "0,25" "0,4" "0,6" "1,0" "1,6" "2,5")
      		list-05 (list "МП")
					list-06 (list "Нет" "Да")
					list-10 (list "С")
		);setq
	);progn
);if

(if (= "Метран-55-ДВ" str-02)
	(progn
		(setq list-03 (list "528")
      		list-04 (list "0,06")
      		list-05 (list "МП")
      		list-06 (list "Нет" "Да")
      		list-10 (list "С" "С2" "ШР")
		);setq
	);progn
);if

(if (= "Метран-55-Ех-ДВ" str-02)
	(progn
		(setq list-03 (list "528")
      		list-04 (list "0,06")
      		list-05 (list "МП")
      		list-06 (list "Нет" "Да")
      		list-10 (list "С" "С2" "ШР")
		);setq
	);progn
);if

(if (= "Метран-55-Вн-ДВ" str-02)
	(progn
		(setq list-03 (list "528")
      		list-04 (list "0,06")
      		list-05 (list "МП")
      		list-06 (list "Нет" "Да")
      		list-10 (list "С")
		);setq
	);progn
);if

(if (= "Метран-55-ДИВ" str-02)
	(progn
		(setq list-03 (list "535")
      		list-04 (list "0,06 разр" "0,1 разр" "0,15" "0,3" "0,5" "0,9" "1,5" "2,4")
      		list-05 (list "МП")
      		list-06 (list "Нет" "Да")
      		list-10 (list "С" "С2" "ШР")
		);setq
	);progn
);if

(if (= "Метран-55-Ех-ДИВ" str-02)
	(progn
		(setq list-03 (list "535")
      		list-04 (list "0,06 разр" "0,1 разр" "0,15" "0,3" "0,5" "0,9" "1,5" "2,4")
      		list-05 (list "МП")
      		list-06 (list "Нет" "Да")
      		list-10 (list "С" "С2" "ШР")
		);setq
	);progn
);if

(if (= "Метран-55-Вн-ДИВ" str-02)
	(progn
		(setq list-03 (list "535")
      		list-04 (list "0,06 разр" "0,1 разр" "0,15" "0,3" "0,5" "0,9" "1,5" "2,4")
      		list-05 (list "МП")
      		list-06 (list "Нет" "Да")
      		list-10 (list "С")
		);setq
	);progn
);if

(list-filling "txt-03" list-03)
(list-filling "txt-04" list-04)
(list-filling "txt-05" list-05)
(list-filling "txt-06" list-06)
(list-filling "txt-10" list-10)

(set_tile "txt-03" "0")
(set_tile "txt-04" "0")
(set_tile "txt-05" "0")
(set_tile "txt-06" "0")
(set_tile "txt-10" "0")

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun txt-03-101-metran-55

( / str-03)

(setq str-03 (nth (atoi (get_tile "txt-03")) list-03)
);setq

(setq list-04
	(cond
		((= str-03 "505") (list "0,25" "0,4" "0,6" "1,0" "1,6" "2,5"));=
		((= str-03 "506") (list "1,6" "2,5" "4,0" "6,0" "10,0" "16,0"));=
		((= str-03 "515") (list "0,25" "0,4" "0,6" "1,0" "1,6" "2,5"));=
		((= str-03 "516") (list "1,6" "2,5" "4,0" "6,0" "10,0" "16,0"));=
		((= str-03 "517") (list "10" "16" "25" "40" "60" "100"));=
		((= str-03 "518") (list "0,06" "0,1" "0,16" "0,25" "0,4" "0,6"));=
		((= str-03 "528") (list "0,06"));=
		((= str-03 "535") (list "0,06 разр" "0,1 разр" "0,15" "0,3" "0,5" "0,9" "1,5" "2,4"));=
	);cond
);setq

(setq list-06
	(cond
		((= str-03 "505") (list "Нет" "Да"));=
		((= str-03 "506") (list "Нет" "Да"));=
		((= str-03 "515") (list "Нет" "Да"));=
		((= str-03 "516") (list "Нет" "Да"));=
		((= str-03 "517") (list "Не выпуск."));=
		((= str-03 "518") (list "Нет" "Да"));=
		((= str-03 "528") (list "Нет" "Да"));=
		((= str-03 "535") (list "Нет" "Да"));=
	);cond
);setq

(list-filling "txt-04" list-04)
(list-filling "txt-06" list-06)

(set_tile "txt-04" "0")
(set_tile "txt-06" "0")

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun txt-04-101-metran-55

( / str-03 str-04)

(setq str-03 (nth (atoi (get_tile "txt-03")) list-03)
			str-04 (nth (atoi (get_tile "txt-04")) list-04)
);setq

(if (= str-03 "505")
	(cond
		((or (= str-04 "0,25") (= str-04 "0,4")) (setq list-05 (list "МП")));=
		((or (= str-04 "0,6") (= str-04 "1,0") (= str-04 "1,6") (= str-04 "2,5"))	(setq list-05 (list "МП" "АП")));=
	);cond
);if

(if (= str-03 "506")
	(cond
		((or (= str-04 "1,6") (= str-04 "2,5")) (setq list-05 (list "МП")));=
		((= str-04 "4,0") (setq list-05 (list "МП" "АП")));=
		((= str-04 "6,0") (setq list-05 (list "МП" "АП")));=
		((= str-04 "10,0") (setq list-05 (list "МП" "АП")));=
		((= str-04 "16,0") (setq list-05 (list "МП" "АП")));=
	);cond
);if

(if (= str-03 "515")
	(cond
		((= str-04 "0,25") (setq list-05 (list "МП")));=
		((= str-04 "0,4") (setq list-05 (list "МП")));=
		((= str-04 "0,6") (setq list-05 (list "МП" "АП")));=
		((= str-04 "1,0") (setq list-05 (list "МП" "АП")));=
		((= str-04 "1,6") (setq list-05 (list "МП" "АП")));=
		((= str-04 "2,5") (setq list-05 (list "МП" "АП")));=
	);cond
);if

(if (= str-03 "516")
	(cond
		((= str-04 "1,6") (setq list-05 (list "МП")));=
		((= str-04 "2,5") (setq list-05 (list "МП")));=
		((= str-04 "4,0") (setq list-05 (list "МП" "АП")));=
		((= str-04 "6,0") (setq list-05 (list "МП" "АП")));=
		((= str-04 "10,0") (setq list-05 (list "МП" "АП")));=
		((= str-04 "16,0") (setq list-05 (list "МП" "АП")));=
	);cond
);if

(if (= str-03 "517")
	(cond
		((= str-04 "10") (setq list-05 (list "МП")));=
		((= str-04 "16") (setq list-05 (list "МП")));=
		((= str-04 "25") (setq list-05 (list "МП" "АП")));=
		((= str-04 "40") (setq list-05 (list "МП" "АП")));=
		((= str-04 "60") (setq list-05 (list "МП" "АП")));=
		((= str-04 "100") (setq list-05 (list "МП" "АП")));=
	);cond
);if

(if (= str-03 "518")
	(cond
		((= str-04 "0,06") (setq list-05 (list "МП")));=
		((= str-04 "0,1") (setq list-05 (list "МП" "АП")));=
		((= str-04 "0,16") (setq list-05 (list "МП" "АП")));=
		((= str-04 "0,25") (setq list-05 (list "МП" "АП")));=
		((= str-04 "0,4") (setq list-05 (list "МП" "АП")));=
		((= str-04 "0,6") (setq list-05 (list "МП" "АП")));=
	);cond
);if

(if (= str-03 "528")
	(cond
		((= str-04 "0,06") (setq list-05 (list "МП")));=
		((= str-04 "0,1") (setq list-05 (list "МП" "АП")));=
	);cond
);if

(if (= str-03 "535")
	(cond
		((= str-04 "0,06 разр") (setq list-05 (list "МП")));=
		((= str-04 "0,1 разр") (setq list-05 (list "АП")));=
		((= str-04 "0,15") (setq list-05 (list "МП")));=
		((= str-04 "0,3") (setq list-05 (list "МП")));=
		((= str-04 "0,5") (setq list-05 (list "МП" "АП")));=
		((= str-04 "0,9") (setq list-05 (list "МП" "АП")));=
		((= str-04 "1,5") (setq list-05 (list "МП" "АП")));=
		((= str-04 "2,4") (setq list-05 (list "МП" "АП")));=
	);cond
);if

(list-filling "txt-05" list-05)

(set_tile "txt-05" "0")

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun txt-05-101-metran-55

( / str-05)

(setq str-05 (nth (atoi (get_tile "txt-05")) list-05)
);setq

(if (= str-05 "МП")
	(setq list-07 (list "УХЛ 3.1 (+5...+50)" "Т3 (-25...+70)" "У2 (-40...+70)")
      	list-08 (list "0,5" "0,25" "0,15")
	);setq
);if

(if (= str-05 "АП")
	(setq list-07 (list "УХЛ 3.1 (+5...+50)" "УХЛ 3.1 (-10...+50)" "УХЛ 3.1 (+5...+70)" "У2 (-30...+50)" "У2 (-42...+50)" "У2 (-42...+70)" 
	"Т3 (-10...+55)" "Т3 (-25...+70)" "Т3 (-25...+55)")
      	list-08 (list "0,5" "1,0")
	);setq
);if

(list-filling "txt-07" list-07)
(list-filling "txt-08" list-08)

(set_tile "txt-07" "0")
(set_tile "txt-08" "0")

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun tmp-1-101-metran-55

( / str-02 str-05)

(setq str-02 (nth (atoi (get_tile "txt-02")) list-02)
			str-05 (nth (atoi (get_tile "txt-05")) list-05)
);setq

(if (= str-05 "МП")
	(cond
		((= "Метран-55-Ех-ДА" str-02) (setq list-09 (list "4-20")));=
		((= "Метран-55-Ех-ДИ" str-02) (setq list-09 (list "4-20")));=
		((= "Метран-55-Ех-ДВ" str-02) (setq list-09 (list "4-20")));=
		((= "Метран-55-Ех-ДИВ" str-02) (setq list-09 (list "4-20")));=
		((= "Метран-55-ДА" str-02) (setq list-09 (list "4-20" "0-5")));=
		((= "Метран-55-Вн-ДА" str-02) (setq list-09 (list "4-20" "0-5")));=
		((= "Метран-55-ДИ" str-02) (setq list-09 (list "4-20" "0-5")));=
		((= "Метран-55-Вн-ДИ" str-02) (setq list-09 (list "4-20" "0-5")));=
		((= "Метран-55-ДВ" str-02) (setq list-09 (list "4-20" "0-5")));=
		((= "Метран-55-Вн-ДВ" str-02) (setq list-09 (list "4-20" "0-5")));=
		((= "Метран-55-ДИВ" str-02) (setq list-09 (list "4-20" "0-5")));=
		((= "Метран-55-Вн-ДИВ" str-02) (setq list-09 (list "4-20" "0-5")));=
	);cond
);if

(if (= str-05 "АП")
	(cond
		((= "Метран-55-Ех-ДА" str-02) (setq list-09 (list "4-20")));=
		((= "Метран-55-Ех-ДИ" str-02) (setq list-09 (list "4-20")));=
		((= "Метран-55-Ех-ДВ" str-02) (setq list-09 (list "4-20")));=
		((= "Метран-55-Ех-ДИВ" str-02) (setq list-09 (list "4-20")));=
		((= "Метран-55-ДА" str-02) (setq list-09 (list "4-20" "0-5" "0-20")));=
		((= "Метран-55-Вн-ДА" str-02) (setq list-09 (list "4-20" "0-5" "0-20")));=
		((= "Метран-55-ДИ" str-02) (setq list-09 (list "4-20" "0-5" "0-20")));=
		((= "Метран-55-Вн-ДИ" str-02) (setq list-09 (list "4-20" "0-5" "0-20")));=
		((= "Метран-55-ДВ" str-02) (setq list-09 (list "4-20" "0-5" "0-20")));=
		((= "Метран-55-Вн-ДВ" str-02) (setq list-09 (list "4-20" "0-5" "0-20")));=
		((= "Метран-55-ДИВ" str-02) (setq list-09 (list "4-20" "0-5" "0-20")));=
		((= "Метран-55-Вн-ДИВ" str-02) (setq list-09 (list "4-20" "0-5" "0-20")));=
	);cond
);if

(list-filling "txt-09" list-09)
(set_tile "txt-09" "0")
(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;подпрограмма формирования данных/////////////////////////////////////////////////////////////////////////////////////////////////////////////////////////////////////////////
(defun tmp-filling-fields-101-metran-55

( / cntr-1 str-01 str-02 str-03 str-04 str-05 str-06 str-07 str-08 str-09 str-10 str-902 str-99 swtch)

;заполняем поле "выбрано"
(setq str-01 (nth (atoi (get_tile "txt-02")) list-02)
			str-02 (nth (atoi (get_tile "txt-03")) list-03)
			str-03 (nth (atoi (get_tile "txt-04")) list-04)
			str-04 (nth (atoi (get_tile "txt-05")) list-05)
			str-05 (nth (atoi (get_tile "txt-06")) list-06)
			str-06 (nth (atoi (get_tile "txt-07")) list-07)
			str-07 (nth (atoi (get_tile "txt-08")) list-08)
			str-08 (nth (atoi (get_tile "txt-09")) list-09)
			str-09 (nth (atoi (get_tile "txt-10")) list-10)
			str-10 (nth (atoi (get_tile "txt-11")) list-11)
      swtch list-901 ;запоминаем первоначальное состояние списка в поле "выбрано"
      cntr-1 0 ;счетчик, номер элемента в списке
      str-99 "0,9" ;масса
);setq

(if (/= swtch nil) (setq list-902 (reverse list-902)));if

(setq str-902 (list (cons 1 str-01) (cons 2 str-02) (cons 3 str-03) (cons 4 str-04) (cons 5 str-05) (cons 6 str-06) (cons 7 str-07)	(cons 8 str-08) 
(cons 9 str-09) (cons 10 str-10) (cons 99 str-99))
  		list-902 (vl-list*  str-902 list-902);список характеристик для спецификации
  		list-901 (vl-list* (strcat str-01 "  Модель " str-02 "  Предел изм. " str-03 "МПа  " str-04 "  Кислородн исп. " str-05 "  " str-06 "  " str-07 "%  " str-08
  		"мА  Ввод кабеля " str-09 "  Монтажн. части " str-10) list-901)
);setq

(setq list-902 (reverse list-902));setq

(list-filling "txt-901" (reverse list-901))

(princ)
)
;;;;////////////////////////////////////////////////////////////////////////////////////////////////////////////////////////////////////////////////////////////////////////////
;;;;////////////////////////////////////////////////////////////////////////////////////////////////////////////////////////////////////////////////////////////////////////////

;;;;////////////////////////////////////////////////////////////////////////////////////////////////////////////////////////////////////////////////////////////////////////////
;;;;подпрограмма вывода в ПЭ                   /////////////////////////////////////////////////////////////////////////////////////////////////////////////////////////////////
(defun tmp-le-101-metran-55

( / cntr-1 dlt-y nmbr-ln pnt-ins tmp tmp-1 tmp-2 tmp-3 tmp-8 x-pnt-ins y-pnt-ins y-pnt-ins-1)

(setq cntr-1 0);setq

(repeat (length list-902)
	(setq tmp (nth cntr-1 list-902)
				tmp-1 (cdr (assoc 1 tmp))
				tmp-2 (cdr (assoc 2 tmp))
				tmp-3 (cdr (assoc 3 tmp))
				tmp-8 (cdr (assoc 8 tmp))
	);setq
		
	(setvar "osmode" 6199)
	
	(setq pnt-ins (getpoint "\nУкажите точку вставки\n")
				str-txt (strcat "Датчик давления " tmp-1 " модель " tmp-2 ", пределы изм. " tmp-3 "МПа, выходной сигнал " tmp-8 "мА")
				str-txt-01 nil
	);setq
	
	(split-str-parts-le-110-01 str-txt str-txt-01 pnt-ins)

	(setq cntr-1 (1+ cntr-1));setq
);repeat

(princ)
)
;;;;///////////////////////////////////////////////////////////////////////////////////////////////////////////////////////////////////////////////////////////////////////////
;;;;///////////////////////////////////////////////////////////////////////////////////////////////////////////////////////////////////////////////////////////////////////////

;;;;////////////////////////////////////////////////////////////////////////////////////////////////////////////////////////////////////////////////////////////////////////////
;;;;подпрограмма вывода в спцф                   ///////////////////////////////////////////////////////////////////////////////////////////////////////////////////////////////
(defun tmp-spcf-101-metran-55

( / cntr-1 dlt-y kol nmbr-ln pnt-ins str-txt tmp tmp-1 tmp-10 tmp-10-1 tmp-1-1 tmp-2 tmp-3 tmp-3-2 tmp-4 tmp-4-2 tmp-5 tmp-5-2 tmp-6 tmp-6-2 tmp-7 tmp-7-2 tmp-8 tmp-8-2 
tmp-9 tmp-9-1 tmp-99 x-pnt-ins y-pnt-ins y-pnt-ins-1)

(setq cntr-1 0
			nmbr-ln 7
			kol 4
);setq

(repeat (length list-902)
	(setq tmp (nth cntr-1 list-902)
				tmp-1 (cdr (assoc 1 tmp))
				tmp-2 (cdr (assoc 2 tmp))
				tmp-3 (cdr (assoc 3 tmp))
				tmp-4 (cdr (assoc 4 tmp))
				tmp-5 (cdr (assoc 5 tmp))
				tmp-6 (cdr (assoc 6 tmp))
				tmp-7 (cdr (assoc 7 tmp))
				tmp-8 (cdr (assoc 8 tmp))
				tmp-9 (cdr (assoc 9 tmp))
				tmp-10 (cdr (assoc 10 tmp))
				tmp-99 (cdr (assoc 99 tmp))
	);setq
	
	(setvar "osmode" 6199)
	
	(setq pnt-ins		(getpoint "\nУкажите точку вставки\n")
	  		x-pnt-ins (nth 0 pnt-ins)
	 			y-pnt-ins (nth 1 pnt-ins)
	  		y-pnt-ins-1 y-pnt-ins
	  		dlt-y 8
	);setq
	
	(101-empt-lin-spcf)

	;////////////////////////////////////////////////////////////////////////////////////////////////////////////////////////////////////////////////////////////////////

	(setq tmp-1-1
		(cond
			((wcmatch tmp-1 "*ДА") "измерение абсолютного давления");=
			((wcmatch tmp-1 "*ДИ") "измерение избыточного давления");=
			((wcmatch tmp-1 "*ДИВ") "измерение давления-разряжения");=
		);cond
	);setq
	
	
	(setq tmp-3-2
		(cond
			((= "0,06 разр" tmp-3) "0,06");=
			((= "0,1 разр" tmp-3) "0,1");=
		);cond
	);setq
 
	(setq tmp-4-2
		(cond
			((= "МП" tmp-4) "-МП");=
			((= "АП" tmp-4) "");=
		);cond
	);setq
	
	(cond
		((= "Нет" tmp-5) 
			(setq tmp-5-2 ""
						nmbr-ln (- nmbr-ln 1)
						kol 3
			);setq
		);=
		((= "Да" tmp-5)
			(progn
				(setq tmp-5-2 "-К"
							kol 4
				);setq
				(command "_text" "_ML" (list (+ x-pnt-ins 5) (- (- y-pnt-ins (* dlt-y 3)) 4)) 2.5 0 "- для работы с кислородом")
			);progn
		);=
	);cond
	
	(setq tmp-6-2
		(cond
			((= "УХЛ 3.1 (+5...+50)" tmp-6) "t1");=
			((= "УХЛ 3.1 (-10...+50)" tmp-6) "t2");=
			((= "УХЛ 3.1 (+5...+70)" tmp-6) "t3");=
			((= "У2 (-30...+50)" tmp-6) "t4");=
			((= "У2 (-42...+50)" tmp-6) "t5");=
			((= "У2 (-42...+70)" tmp-6) "t6");=
			((= "Т3 (-10...+55)" tmp-6) "t7");=
			((= "Т3 (-25...+70)" tmp-6) "t8");=
			((= "Т3 (-25...+55)" tmp-6) "t9");=
		);cond
	);setq

  (if (= "МП" tmp-4)
  	(setq tmp-7-2
			(cond
				((= "0,5" tmp-7) "050");=
				((= "0,25" tmp-7) "025");=
				((= "0,15" tmp-7) "015");=
			);cond
		);setq
	);if
	  
  (if (= "АП" tmp-4) (setq tmp-7-2 tmp-7));if

	(setq tmp-8-2
		(cond
			((= "4-20" tmp-8) "42");=
			((= "0-5" tmp-8) "05");=
			((= "0-20" tmp-8) "02");=
		);cond
	);setq

	(setq tmp-9-1
		(cond
			((= "С" tmp-9) "- cальниковый ввод, для кабеля диаметром не более 10мм.");=
			((= "С2" tmp-9) "- cальниковый ввод с фиксацией кабеля");=
			((= "ШР" tmp-9) "- штепсельный разъем");=
		);cond
	);setq

	(setq tmp-10-1
		(cond
			((= "М20" tmp-10) "- ниппель с накидной гайкой М20х1,5");=
			((= "М20-Кр" tmp-10) "- ниппель с накидной гайкой М20х1,5, кронштейн");=
			((= "М12" tmp-10) "- штуцер М12х1,5");=
			((= "М12-Кр" tmp-10) "- штуцер М12х1,5, кронштейн");=
			((= "КБуст" tmp-10) "- клапанный блок, установленный на датчик давления");=
		);cond
	);setq
	
	(1000-delete-items-spcf nmbr-ln pnt-ins)
	(1000-delete-items-spcf-crtf nmbr-ln pnt-ins)
				
	(setq str-txt (strcat tmp-1 "-" tmp-2 tmp-5-2 tmp-4-2 "-" tmp-6-2 "-" tmp-7-2 "-" tmp-3 "МПа-" tmp-8-2 "-" tmp-9 "/" tmp-10));setq
			
	(command "_text" "_ML" (list (+ x-pnt-ins 1) (- (- y-pnt-ins (* dlt-y 0)) 4)) 2.5 0 "Датчик давления")
	(command "_text" "_ML" (list (+ x-pnt-ins 5) (- (- y-pnt-ins (* dlt-y 1)) 4)) 2.5 0 (strcat "- " tmp-1-1 ", эл. преобразователь " tmp-4))
	(command "_text" "_ML" (list (+ x-pnt-ins 5) (- (- y-pnt-ins (* dlt-y 2)) 4)) 2.5 0 (strcat "- климатическое исполнение " tmp-6))
	(command "_text" "_ML" (list (+ x-pnt-ins 5) (- (- y-pnt-ins (* dlt-y kol)) 4)) 2.5 0 (strcat "- предел допускаемой осн. погрешности " tmp-7 "%, вых. сигнал " tmp-8 "мА"))
	(command "_text" "_ML" (list (+ x-pnt-ins 5) (- (- y-pnt-ins (* dlt-y (+ 1 kol))) 4)) 2.5 0 tmp-9-1)
	(command "_text" "_ML" (list (+ x-pnt-ins 5) (- (- y-pnt-ins (* dlt-y (+ 2 kol))) 4)) 2.5 0 tmp-10-1)
	;
	(split-str-parts-spcf-60-01 str-txt nil pnt-ins)
	;
	(print-number-certificate "№34341" pnt-ins)

	(repeat nmbr-ln
  	(command "_insert" "зс-пустая-строка" "_X" 1 "_Y" 1 "_Z" 1 "_R" 0 (list x-pnt-ins y-pnt-ins-1))
  	(setq y-pnt-ins-1 (- y-pnt-ins-1 8));setq
	);repeat
								
	(command "_text" "_MC" (list (+ x-pnt-ins 247.5) (- (- y-pnt-ins (* dlt-y 0)) 4)) 2.5 0 "ПГ \"Метран\",")
	(command "_text" "_MC" (list (+ x-pnt-ins 247.5) (- (- y-pnt-ins (* dlt-y 1)) 4)) 2.5 0 "г. Челябинск")	
	(command "_text" "_MC" (list (+ x-pnt-ins 280) (- (- y-pnt-ins (* dlt-y 0)) 4)) 2.5 0 "шт.")

	(command "_text" "_MC" (list (+ x-pnt-ins 322.5) (- (- y-pnt-ins (* dlt-y 0)) 4)) 2.5 0 tmp-99)
 
	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////
