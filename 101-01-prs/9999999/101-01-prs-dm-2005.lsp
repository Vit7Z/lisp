;/////// ************************************************************ ///////////////////////////////////////////////////////////////////////////////////////////////////////////
;///////                                                              ///////////////////////////////////////////////////////////////////////////////////////////////////////////
;/////// ************************************************************ ///////////////////////////////////////////////////////////////////////////////////////////////////////////
(defun 101-01-press-dm-2005

( / adoc counter dcl-id list-01 list-02 list-03 list-04 list-05 list-06 list-07 list-901 list-902 str-01 type-list)

(vl-load-com)
(vla-startundomark (setq adoc (vla-get-activedocument (vlax-get-acad-object))));start undo

(setq str-01 nil
      counter 0
      list-01 (list "ДМ 2005")
      list-901 nil
      list-902 nil
);setq

(tmp-strt-101-01-press-dm-2005)

(if (< (setq dcl-id (load_dialog "dia-101-01-press-dm-2005.dcl")) 0) ;ищем диалог
		(progn
			(alert "Не найден dcl-файл")
			(exit)
		);progn
);if

(if (not (new_dialog "dia_101_dm_2005" dcl-id))
		(exit)
);if

(list-filling "txt-01" list-01)
(list-filling "txt-02" list-02)
(list-filling "txt-03" list-03)
(list-filling "txt-04" list-04)
(list-filling "txt-05" list-05)
(list-filling "txt-06" list-06)
(list-filling "txt-07" list-07)

(set_tile "txt-01" "0")
(set_tile "txt-02" "0")
(set_tile "txt-03" "0")
(set_tile "txt-04" "0")
(set_tile "txt-05" "0")
(set_tile "txt-06" "0")
(set_tile "txt-07" "0")

(action_tile "txt-01"
  (strcat "(tmp-strt-101-01-press-dm-2005)");strcat
);action_tile

(action_tile "txt-02"
  (strcat "(txt-02-101-01-press-dm-2005)");strcat
);action_tile

(action_tile "txt-03"
  (strcat "(txt-03-101-01-press-dm-2005)");strcat
);action_tile

(action_tile "but1"
  (strcat "(tmp-filling-fields-101-01-press-dm-2005)");strcat
);action_tile

(action_tile "but2"
  (strcat "(setq type-list \"le\")"
          "(done_dialog)"
  );strcat
);action_tile

(action_tile "but3"
  (strcat "(setq type-list \"spcf\")"
          "(done_dialog)"
  );strcat
);action_tile

(action_tile "accept"
  (strcat "(done_dialog)"
          "(exit)"
  );strcat
);action_tile

(start_dialog)
(unload_dialog dcl-id)

(if (= type-list "le") (tmp-le-101-01-press-dm-2005));if

(if (= type-list "spcf") (tmp-spcf-101-01-press-dm-2005));if

(setvar "osmode" 6199)
(setvar "cmdecho" 1)
(vla-endundomark adoc)
(princ)
)
;/////// конец программы ////////////////////////////////////////////////////////////////////////////////////////////////////////////////////////////////////////////////////////


;;;;/////////////////////////////////////////////////////////////////////////////////////////////////////////////////////////////////////////////////////////////////////////////
;;;;/////////////////////////////////////////////////////////////////////////////////////////////////////////////////////////////////////////////////////////////////////////////
(defun tmp-strt-101-01-press-dm-2005

()

(if (= nil str-01) 
	(setq str-01 "ДМ 2005");setq
	(setq str-01 (nth (atoi (get_tile "txt-01")) list-01));setq
);if

(if (= "ДМ 2005" str-01)
	(progn
		(setq list-02 (list "1,5" "1")
					list-03 (list "кгс/см2" "МПа")
					list-04 (list "0...1" "0...1,6" "0...2,5" "0...4" "0...6" "0...10" "0...16" "0...25" "0...40" "0...60" "0...100" "0...160" "0...250" "0...400" "0...600" 
												"0...1000" "0...1600")
      		list-05 (list "IP40" "IP54")
      		list-06 (list "Без фланца" "С задним фланцем")
      		list-07 (list "V (1НЗ, 1НО)" "III (2НЗ)" "IV (2НО)" "VI (1НО, 1НЗ)")
		);setq
	);progn
);if

(list-filling "txt-02" list-02)
(list-filling "txt-03" list-03)
(list-filling "txt-04" list-04)
(list-filling "txt-05" list-05)
(list-filling "txt-06" list-06)
(list-filling "txt-07" list-07)

(set_tile "txt-02" "0")
(set_tile "txt-03" "0")
(set_tile "txt-04" "0")
(set_tile "txt-05" "0")
(set_tile "txt-06" "0")
(set_tile "txt-07" "0")

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun txt-02-101-01-press-dm-2005

( / str-01 str-02)

(setq str-01 (nth (atoi (get_tile "txt-01")) list-01)
			str-02 (nth (atoi (get_tile "txt-02")) list-02)
);setq

(if (= "ДМ 2005" str-01)
	(if (= "1,5" str-02)
		(setq list-04 (list "0...1" "0...1,6" "0...2,5" "0...4" "0...6" "0...10" "0...16" "0...25" "0...40" "0...60" "0...100" "0...160" "0...250" "0...400" "0...600" 
												"0...1000" "0...1600")
		);setq
	);if
);if

(if (= "ДМ 2005" str-01)
	(if (= "1" str-02)
		(setq list-04 (list "0...4" "0...6" "0...10" "0...16" "0...25" "0...40" "0...60" "0...100" "0...160" "0...250" "0...400" "0...600")
		);setq
	);if
);if

(list-filling "txt-04" list-04)

(set_tile "txt-04" "0")

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun txt-03-101-01-press-dm-2005

( / str-02 str-03)

(setq str-01 (nth (atoi (get_tile "txt-01")) list-01)
			str-02 (nth (atoi (get_tile "txt-02")) list-02)
			str-03 (nth (atoi (get_tile "txt-03")) list-03)
);setq

(if (and (= "ДМ 2005" str-01) (= "1,5" str-02) (= "кгс/см2" str-03))
	(setq list-04 (list "0...1" "0...1,6" "0...2,5" "0...4" "0...6" "0...10" "0...16" "0...25" "0...40" "0...60" "0...100" "0...160" "0...250" "0...400" "0...600" 
											"0...1000" "0...1600")
	);setq
);if

(if (and (= "ДМ 2005" str-01) (= "1" str-02) (= "кгс/см2" str-03))
	(setq list-04 (list "0...4" "0...6" "0...10" "0...16" "0...25" "0...40" "0...60" "0...100" "0...160" "0...250" "0...400" "0...600")
	);setq
);if

(if (and (= "ДМ 2005" str-01) (= "1,5" str-02) (= "МПа" str-03))
	(setq list-04 (list "0...0,1" "0...0,16" "0...0,25" "0...0,4" "0...0,6" "0...1" "0...1,6" "0...2,5" "0...4" "0...6" "0...10" "0...16" "0...25" "0...40" "0...60" 
											"0...100" "0...160")
	);setq
);if

(if (and (= "ДМ 2005" str-01) (= "1" str-02) (= "МПа" str-03))
	(setq list-04 (list "0...0,4" "0...0,6" "0...1" "0...1,6" "0...2,5" "0...4" "0...6" "0...10" "0...16" "0...25" "0...40" "0...60")
	);setq
);if


(list-filling "txt-04" list-04)

(set_tile "txt-04" "0")

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;подпрограмма формирования данных/////////////////////////////////////////////////////////////////////////////////////////////////////////////////////////////////////////////
(defun tmp-filling-fields-101-01-press-dm-2005

( / str-01 str-02 str-03 str-04 str-05 str-06 str-07 str-902 str-99 swtch)

;заполняем поле "выбрано"
(setq str-01 (nth (atoi (get_tile "txt-01")) list-01)
			str-02 (nth (atoi (get_tile "txt-02")) list-02)
			str-03 (nth (atoi (get_tile "txt-03")) list-03)
			str-04 (nth (atoi (get_tile "txt-04")) list-04)
			str-05 (nth (atoi (get_tile "txt-05")) list-05)
			str-06 (nth (atoi (get_tile "txt-06")) list-06)
			str-07 (nth (atoi (get_tile "txt-07")) list-07)
);setq

(if (/= swtch nil) (setq list-902 (reverse list-902)));if

(setq str-99 "0,9");setq

(setq str-902 (list (cons 1 str-01) (cons 2 str-02) (cons 3 str-03) (cons 4 str-04) (cons 5 str-05) (cons 6 str-06) (cons 7 str-07) (cons 99 str-99))
  				list-902 (vl-list* str-902 list-902);список характеристик для спецификации
  				list-901 (vl-list* (strcat str-01 "  "
  																 	 str-04 str-03 "  "
  																 	 str-05 "  " 
  																 	 str-06 "  "
  																 	 "Класс точности " str-02 "  "
  																 	 "Исп. контактов " str-07) list-901)
);setq

(setq list-902 (reverse list-902));setq

(list-filling "txt-901" (reverse list-901))

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;подпрограмма вывода в ПЭ                   //////////////////////////////////////////////////////////////////////////////////////////////////////////////////////////////////
(defun tmp-le-101-01-press-dm-2005

( / cntr-1 pnt-ins str-701 str-702 str-tmp str-tmp-1 str-tmp-2 str-tmp-3 str-tmp-4 str-tmp-7)

(setq cntr-1 0);setq

(repeat (length list-902)
	(setq str-tmp (nth cntr-1 list-902)
				str-tmp-1 (cdr (assoc 1 str-tmp))
				str-tmp-2 (cdr (assoc 2 str-tmp))
				str-tmp-3 (cdr (assoc 3 str-tmp))
				str-tmp-4 (cdr (assoc 4 str-tmp))
				str-tmp-7 (cdr (assoc 7 str-tmp))
	);setq

	(setvar "osmode" 6199)
	
	(setq pnt-ins		(getpoint "\nУкажите точку вставки\n"));setq
	
	(if (= "ДМ 2005" str-tmp-1)
		(setq str-701 (strcat "Манометр электроконтактный ДМ 2005, пределы изм. " str-tmp-4 str-tmp-3 ", класс точности " str-tmp-2 ", исп. контактов " str-tmp-7)
					str-702 nil
		);setq
	);if

	(split-str-parts-le-01-general str-701 str-702 pnt-ins);

	(setq cntr-1 (1+ cntr-1));setq

);repeat

(princ)
)
;;;;/////////////////////////////////////////////////////////////////////////////////////////////////////////////////////////////////////////////////////////////////////////////
;;;;/////////////////////////////////////////////////////////////////////////////////////////////////////////////////////////////////////////////////////////////////////////////


;;;;/////////////////////////////////////////////////////////////////////////////////////////////////////////////////////////////////////////////////////////////////////////////
;;;;подпрограмма вывода в спцф                   ////////////////////////////////////////////////////////////////////////////////////////////////////////////////////////////////
(defun tmp-spcf-101-01-press-dm-2005

( / cntr-1 dlt-y kol nmbr-ln pnt-ins str-not str-patrn str-tmp str-tmp-1 str-tmp-2 str-tmp-3 str-tmp-4 str-tmp-5 str-tmp-6 str-tmp-7 str-tmp-99 str-txt x-pnt-ins y-pnt-ins 
y-pnt-ins-1)

(setvar "textstyle" "Standard")

(setq cntr-1 0);setq

(repeat (length list-902)
	(setq str-tmp (nth cntr-1 list-902)
				str-tmp-1 (cdr (assoc 1 str-tmp))
				str-tmp-2 (cdr (assoc 2 str-tmp))
				str-tmp-3 (cdr (assoc 3 str-tmp))
				str-tmp-4 (cdr (assoc 4 str-tmp))
				str-tmp-5 (cdr (assoc 5 str-tmp))
				str-tmp-6 (cdr (assoc 6 str-tmp))
				str-tmp-7 (cdr (assoc 7 str-tmp))
				str-tmp-99 (cdr (assoc 99 str-tmp))
	);setq

;	(princ "\n         str-tmp = ") (princ str-tmp);Erase_DV
;	(getstring "\nPress Enter to continue...");Erase_DV
			
	(setvar "osmode" 6199)
	
	(setq pnt-ins (getpoint "\nУкажите точку вставки\n"));setq
	
	(cond
		((= str-tmp-6 "Без фланца") (setq str-tmp-6 "радиальный штуцер без фланца"));=
		((= str-tmp-6 "С задним фланцем") (setq str-tmp-6 "радиальный штуцер с задним фланцем"));=
	);cond

	;/////////////////////////////////////////////////////////////////////////////////////////////////
	(if (= str-tmp-1 "ДМ 2005")
		(progn
			(setq nmbr-ln 4
						str-txt (strcat str-tmp-1 " " str-tmp-4 str-tmp-3 ", исп. " str-tmp-7)
						str-not nil
						str-patrn " "
			);setq
			
			(1000-delete-items-spcf nmbr-ln pnt-ins)
			(1000-delete-items-spcf-crtf nmbr-ln pnt-ins)

			(command "_text" "_ML" (list (+ x-pnt-ins 1) (- (- y-pnt-ins (* dlt-y 0)) 4)) 2.5 0 "Манометр электроконтактный")
			(command "_text" "_ML" (list (+ x-pnt-ins 5) (- (- y-pnt-ins (* dlt-y 1)) 4)) 2.5 0 (strcat "- пределы изм. " str-tmp-4 str-tmp-3 ", класс точности " str-tmp-2 ", степень защиты " str-tmp-5))
			(command "_text" "_ML" (list (+ x-pnt-ins 5) (- (- y-pnt-ins (* dlt-y 2)) 4)) 2.5 0 (strcat "- " str-tmp-6 ", исп. контактов " str-tmp-7))
		);progn
	);if

	(split-str-parts-spcf-60-01 str-txt str-not str-patrn pnt-ins);

	(command "_text" "_MC" (list (+ x-pnt-ins 247.5) (- (- y-pnt-ins (* dlt-y 0)) 4)) 2.5 0 "ОАО \"Манотомь\",")
	(command "_text" "_MC" (list (+ x-pnt-ins 247.5) (- (- y-pnt-ins (* dlt-y 1)) 4)) 2.5 0 "г. Томск")
	(command "_text" "_MC" (list (+ x-pnt-ins 322.5) (- (- y-pnt-ins (* dlt-y 0)) 4)) 2.5 0 str-tmp-99);масса
	(command "_text" "_MC" (list (+ x-pnt-ins 280) (- (- y-pnt-ins (* dlt-y 0)) 4)) 2.5 0 "шт.")

	(print-number-certificate "№ 42246" pnt-ins)

	(repeat nmbr-ln
		(command "_insert" "зс-пустая-строка" "_X" 1 "_Y" 1 "_Z" 1 "_R" 0 (list x-pnt-ins y-pnt-ins-1))
		(setq y-pnt-ins-1 (- y-pnt-ins-1 8));setq
	);repeat

	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////
