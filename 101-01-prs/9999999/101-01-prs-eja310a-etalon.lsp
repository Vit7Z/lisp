;/////// ************************************************************ ///////////////////////////////////////////////////////////////////////////////////////////////////////////
;///////                                                              ///////////////////////////////////////////////////////////////////////////////////////////////////////////
;/////// ************************************************************ ///////////////////////////////////////////////////////////////////////////////////////////////////////////
(defun 101-eja310a-etalon

( / adoc dcl-id list-10 list-15 list-16 list-17 list-18 list-21 list-22 list-23 list-24 list-25 list-31 list-32 list-33 list-34 list-35 list-36 num-lin pnt-ins txt-10 txt-11 
txt-110 txt-12 txt-13 txt-14 txt-15 txt-15-1 txt-15-2 txt-16 txt-16-1 txt-16-2 txt-16-3 txt-17 txt-17-1 txt-17-2 txt-18 txt-18-1 txt-18-2 txt-18-3 txt-19 txt-21 txt-21-1 
txt-21-2 txt-22 txt-22-1 txt-22-2 txt-22-3 txt-23 txt-23-1 txt-23-2 txt-24 txt-24-1 txt-24-2 txt-25 txt-25-1 txt-25-2 txt-31 txt-31-1 txt-31-2 txt-32 txt-32-1 txt-32-2 txt-33 
txt-33-1 txt-33-2 txt-ins-1 x-pnt-ins y-pnt-ins ypnt-ins-1)

(vl-load-com)
(vla-startundomark
  (setq adoc (vla-get-activedocument (vlax-get-acad-object))
  );setq
);start undo

(setq num-lin 20 ;количество строк
      list-10 (list "Вода" "Насыщенный пар" "Перегретый пар" "Газ природный" "Нефть" "Кислород")
      list-15 (list "4...20мА, HART" "4...20мА, BRAIN" "FOUNDATION Fieldbus")
      list-16 (list "0...0,01 (абс.) (0,00067...0,01) (абс.)" 
                    "0...0,13 (абс.) (0,0013...0,13) (абс.)" 
                    "0...3 (абс.) (0,03...3) (абс.)")
      list-17 (list "Нерж. сталь (фланцы), Hastelloy C-276 (капсула), Нерж. сталь (клапаны)")
      list-18 (list "Без фланцев-переходников, R1/4\", внутр., (BSPT) ГОСТ 6211-81"
                    "Без фланцев-переходников, К1/4\", внутр., (NPT) ГОСТ 6111-52"
                    "C фланцами-переходниками, R1/4\", внутр., (BSPT) ГОСТ 6211-81"
                    "C фланцами-переходниками, R1/2\", внутр., (BSPT) ГОСТ 6211-81"
                    "C фланцами-переходниками, К1/4\", внутр., (NPT) ГОСТ 6111-52"
                    "C фланцами-переходниками, К1/2\", внутр., (NPT) ГОСТ 6111-52")
      list-21 (list "Углеродистая сталь SCM435"
                    "Нержавеющая сталь SUS630"
                    "Нержавеющая сталь SUH630")          
      list-22 (list "Подвод имп. труб вертик., высок. давл. справа, присоединен. сверху"
                    "Подвод имп. труб вертик., высок. давл. справа, присоединен. снизу"
                    "Подвод имп. труб вертик., высок. давл. слева, присоединен. сверху"
                    "Подвод имп. труб вертик., высок. давл. слева, присоединен. снизу"
                    "Подвод имп. труб гориз., высок. давл. справа, присоединен. гориз."
                    "Подвод имп. труб гориз., высок. давл. слева, присоединен. гориз.")
      list-23 (list "М20х1,5" 
                     "G1/2 (BSP) ГОСТ 6357-81"
                     "К1/2 (NPT) ГОСТ 6111-52"
                     "Pg 13,5") 
      list-24 (list "ЖК дисплей" "ЖК дисплей, переключ. шкалы" "Отсутствует")                           
      list-25 (list "Прямой, углеродистая сталь" "Нет" "Прямой, нержавеющая сталь" "Г-образный, углеродистая сталь" "Г-образный, нержавеющая сталь")           
      list-31 (list "Да")
      list-32 (list "Обыкновенная" "Повышенная")
      list-33 (list "Обычное, IP67" "0ExiaIICT5X" "1ExdIICT4...T6")
      list-34 (list "Нет"
                    "Обезжиривание контактирующих частей"
                    "Обезжиривание контактирующих частей, гидрозаполнение фторированным маслом")
      list-35 (list "Нет" "Бар" "Кгс/см2")      
      list-36 (list "Нет" "Нержавеющая сталь SCS14A")      
);setq

(if (< (setq dcl-id (load_dialog "dia-101-eja310a-etalon.dcl")) 0) ;ищем диалог
		(progn
			(alert "Не найден dcl-файл")
			(exit)
		);progn
);if

(if (not (new_dialog "dia_101_eja_530_etalon" dcl-id))
		(exit)
);if

;среда
(list-filling "txt-10" list-10)
(set_tile "txt-10" "0")

;диапазон шкалы датчика
(list-filling "txt-15" list-15)
(set_tile "txt-15" "0")

;погрешность
(list-filling "txt-16" list-16)
(set_tile "txt-16" "0")

;протокол
(list-filling "txt-17" list-17)
(set_tile "txt-17" "0")

(list-filling "txt-18" list-18)
(set_tile "txt-18" "0")

(list-filling "txt-21" list-21)
(set_tile "txt-21" "0")

(list-filling "txt-22" list-22)
(set_tile "txt-22" "0")

(list-filling "txt-23" list-23)
(set_tile "txt-23" "0")

(list-filling "txt-24" list-24)
(set_tile "txt-24" "0")

(list-filling "txt-25" list-25)
(set_tile "txt-25" "0")

(list-filling "txt-31" list-31)
(set_tile "txt-31" "0")

(list-filling "txt-32" list-32)
(set_tile "txt-32" "0")

(list-filling "txt-33" list-33)
(set_tile "txt-33" "0")

(list-filling "txt-34" list-34)
(set_tile "txt-34" "0")

(list-filling "txt-35" list-35)
(set_tile "txt-35" "0")

(list-filling "txt-36" list-36)
(set_tile "txt-36" "0")

(action_tile "txt-15" ;выбор выходного сигнала
  (strcat "(tmp-1-101-eja310a-etalon)"
  );strcat
);action_tile

(action_tile "txt-17" ;выбор выходного сигнала
  (strcat "(tmp-2-101-eja310a-etalon $value)"
  );strcat
);action_tile

(action_tile "accept"
  (strcat "(setq txt-10 (nth (atoi (get_tile \"txt-10\")) list-10))"
          "(setq txt-11 (get_tile \"txt-11\"))"
          "(setq txt-12 (get_tile \"txt-12\"))"
          "(setq txt-13 (get_tile \"txt-13\"))"
          "(setq txt-14 (get_tile \"txt-14\"))"
          "(setq txt-15 (nth (atoi (get_tile \"txt-15\")) list-15))"
          "(setq txt-16 (nth (atoi (get_tile \"txt-16\")) list-16))"
          "(setq txt-19 (get_tile \"txt-19\"))"
          "(setq txt-110 (get_tile \"txt-110\"))"
          "(setq txt-17 (nth (atoi (get_tile \"txt-17\")) list-17))"
          "(setq txt-18 (nth (atoi (get_tile \"txt-18\")) list-18))"
          "(setq txt-21 (nth (atoi (get_tile \"txt-21\")) list-21))"
          "(setq txt-22 (nth (atoi (get_tile \"txt-22\")) list-22))"
          "(setq txt-23 (nth (atoi (get_tile \"txt-23\")) list-23))"
          "(setq txt-24 (nth (atoi (get_tile \"txt-24\")) list-24))"
          "(setq txt-25 (nth (atoi (get_tile \"txt-25\")) list-25))"
          "(setq txt-31 (nth (atoi (get_tile \"txt-31\")) list-31))"
          "(setq txt-32 (nth (atoi (get_tile \"txt-32\")) list-32))"
          "(setq txt-33 (nth (atoi (get_tile \"txt-33\")) list-33))"
          "(done_dialog)"
  );strcat
);action_tile

(action_tile "cancel"
  (strcat "(done_dialog)"
          "(exit)")
);action_tile

(start_dialog)
(unload_dialog dcl-id)


;//////////////////////////////////////////////////
(if (= txt-15 "4...20мА, HART")
  (setq txt-15-1 "-E"
        txt-15-2 "- выходной сигнал 4...20мА, HART"
  );setq
);if

(if (= txt-15 "4...20мА, BRAIN")
  (setq txt-15-1 "-D"
        txt-15-2 "- выходной сигнал 4...20мА, BRAIN"
  );setq
);if

(if (= txt-15 "FOUNDATION Fieldbus")
  (setq txt-15-1 "-F"
        txt-15-2 "- выходной сигнал FOUNDATION Fieldbus"
  );setq
);if

;//////////////////////////////////////////////////
(if (= txt-16 "0...0,01 (абс.) (0,00067...0,01) (абс.)")  
  (setq txt-16-1 "L"
        txt-16-2 "- пределы измерений датчика 0...0,01 (абс.) МПа"
        txt-16-3 "- пределы перенастройки 0,00067...0,01 (абс.) МПа"
  );setq
);if

(if (= txt-16 "0...0,13 (абс.) (0,0013...0,13) (абс.)")  
  (setq txt-16-1 "M"
        txt-16-2 "- пределы измерений датчика 0...0,13 (абс.) МПа"
        txt-16-3 "- пределы перенастройки 0,0013...0,13 (абс.) МПа"
  );setq
);if

(if (= txt-16 "0...3 (абс.) (0,03...3) (абс.)")  
  (setq txt-16-1 "A"
        txt-16-2 "- пределы измерений датчика 0...3 (абс.) МПа"
        txt-16-3 "- пределы перенастройки 0,03...3 (абс.) МПа"
  );setq
);if

;//////////////////////////////////////////////////
(if (= txt-17 "Нерж. сталь (фланцы), Hastelloy C-276 (капсула), Нерж. сталь (клапаны)")
  (setq txt-17-1 "S"
        txt-17-2 "- нерж. сталь (фланцы), Hastelloy C-276 (капсула), нерж. сталь (клапаны)"
  );setq
);if

;//////////////////////////////////////////////////
(if (= txt-18 "Без фланцев-переходников, R1/4\", внутр., (BSPT) ГОСТ 6211-81")
  (setq txt-18-1 "0"
        txt-18-2 "- присоединение к процессу без фланцев-переходников, резьба внутр."
        txt-18-3 "R1/4 (BSPT) ГОСТ 6211-81"
  );setq
);if

(if (= txt-18 "Без фланцев-переходников, К1/4\", внутр., (NPT) ГОСТ 6111-52")
  (setq txt-18-1 "5"
        txt-18-2 "- присоединение к процессу без фланцев-переходников, резьба внутр."
        txt-18-3 "K1/4 (NPT) ГОСТ 6111-52"
  );setq
);if

(if (= txt-18 "C фланцами-переходниками, R1/4\", внутр., (BSPT) ГОСТ 6211-81")
  (setq txt-18-1 "1"
        txt-18-2 "- присоединение к процессу с фланцами-переходниками, резьба внутр."
        txt-18-3 "R1/4 (BSPT) ГОСТ 6211-81"
  );setq
);if

(if (= txt-18 "C фланцами-переходниками, R1/2\", внутр., (BSPT) ГОСТ 6211-81")
  (setq txt-18-1 "2"
        txt-18-2 "- присоединение к процессу с фланцами-переходниками, резьба внутр."
        txt-18-3 "R1/2 (BSPT) ГОСТ 6211-81"
  );setq
);if

(if (= txt-18 "C фланцами-переходниками, К1/4\", внутр., (NPT) ГОСТ 6111-52")
  (setq txt-18-1 "3"
        txt-18-2 "- присоединение к процессу с фланцами-переходниками, резьба внутр."
        txt-18-3 "K1/4 (NPT) ГОСТ 6111-52"
  );setq
);if

(if (= txt-18 "C фланцами-переходниками, К1/2\", внутр., (NPT) ГОСТ 6111-52")
  (setq txt-18-1 "4"
        txt-18-2 "- присоединение к процессу с фланцами-переходниками, резьба внутр."
        txt-18-3 "K1/2 (NPT) ГОСТ 6111-52"
  );setq
);if

;//////////////////////////////////////////////////
(if (= txt-21 "Углеродистая сталь SCM435")
  (setq txt-21-1 "A"
        txt-21-2 "- материал стяжных болтов (гаек) углеродистая сталь SCM435"
  );setq
);if

(if (= txt-21 "Нержавеющая сталь SUS630")
  (setq txt-21-1 "B"
        txt-21-2 "- материал стяжных болтов (гаек) нержавеющая сталь SUS630"
  );setq
);if

(if (= txt-21 "Нержавеющая сталь SUH660")
  (setq txt-21-1 "C"
        txt-21-2 "- материал стяжных болтов (гаек) нержавеющая сталь SUH660"
  );setq
);if

;//////////////////////////////////////////////////
(if (= txt-22 "Подвод имп. труб вертик., высок. давл. справа, присоединен. сверху")               
  (setq txt-22-1 "-2"
        txt-22-2 "- подвод импульсных труб вертикально,"
        txt-22-3 "высокое давление справа, присоединение сверху"
  );setq
);if

(if (= txt-22 "Подвод имп. труб вертик., высок. давл. справа, присоединен. снизу")               
  (setq txt-22-1 "-3"
        txt-22-2 "- подвод импульсных труб вертикально,"
        txt-22-3 "высокое давление справа, присоединение снизу"
  );setq
);if

(if (= txt-22 "Подвод имп. труб вертик., высок. давл. слева, присоединен. сверху")               
  (setq txt-22-1 "-6"
        txt-22-2 "- подвод импульсных труб вертикально,"
        txt-22-3 "высокое давление слева, присоединение сверху"
  );setq
);if

(if (= txt-22 "Подвод имп. труб вертик., высок. давл. слева, присоединен. снизу")               
  (setq txt-22-1 "-7"
        txt-22-2 "- подвод импульсных труб вертикально,"
        txt-22-3 "высокое давление слева, присоединение снизу"
  );setq
);if

(if (= txt-22 "Подвод имп. труб гориз., высок. давл. справа, присоединен. гориз.")               
  (setq txt-22-1 "-8"
        txt-22-2 "- подвод импульсных труб горизонтально,"
        txt-22-3 "высокое давление справа, присоединение горизонтально"
  );setq
);if

(if (= txt-22 "Подвод имп. труб гориз., высок. давл. слева, присоединен. гориз.")               
  (setq txt-22-1 "-9"
        txt-22-2 "- подвод импульсных труб горизонтально,"
        txt-22-3 "высокое давление слева, присоединение горизонтально"
  );setq
);if

;//////////////////////////////////////////////////
(if (= txt-23 "М20х1,5")               
  (setq txt-23-1 "4"
        txt-23-2 "- кабельный ввод М20х1,5"
  );setq
);if

(if (= txt-23 "G1/2 (BSP) ГОСТ 6357-81")
  (setq txt-23-1 "5"
        txt-23-2 "- кабельный ввод G1/2 (BSP) ГОСТ 6357-81"  
  );setq
);if

(if (= txt-23 "К1/2 (NPT) ГОСТ 6111-52")
  (setq txt-23-1 "7"
        txt-23-2 "- кабельный ввод К1/2 (NPT) ГОСТ 6111-52"
  );setq
);if

(if (= txt-23 "Pg 13,5")
  (setq txt-23-1 "8"
        txt-23-2 "- кабельный ввод Pg 13,5"
  );setq
);if

;//////////////////////////////////////////////////
(if (= txt-24 "Отсутствует") 
  (setq txt-24-1 "N"
        txt-24-2 "- индикатор отсутствует"
  );setq
);if

(if (= txt-24 "ЖК дисплей")
  (setq txt-24-1 "D"
        txt-24-2 "- индикатор стандартный"
  );setq
);if

(if (= txt-24 "ЖК дисплей, переключ. шкалы")
  (setq txt-24-1 "E"
        txt-24-2 "- индикатор стандартный, с переключателем шкалы"
  );setq
);if

;//////////////////////////////////////////////////
(if (= txt-25 "Нет")                  
  (setq txt-25-1 "N"
        txt-25-2 "- монтажный кронштейн нет"
  );setq
);if

(if (= txt-25 "Прямой, углеродистая сталь")
  (setq txt-25-1 "E"
        txt-25-2 "- монтажный кронштейн прямой, углеродистая сталь"
  );setq
);if

(if (= txt-25 "Прямой, нержавеющая сталь")
  (setq txt-25-1 "F"
        txt-25-2 "- монтажный кронштейн прямой, нержавеющая сталь"
  );setq
);if

(if (= txt-25 "Г-образный, углеродистая сталь")
  (setq txt-25-1 "E"
        txt-25-2 "- монтажный кронштейн Г-образный, углеродистая сталь"
  );setq
);if

(if (= txt-25 "Г-образный, нержавеющая сталь")
  (setq txt-25-1 "F"
        txt-25-2 "- монтажный кронштейн Г-образный, нержавеющая сталь"
  );setq
);if

;//////////////////////////////////////////////////
(if (= txt-31 "Да")                  
  (setq txt-31-1 "/QR"
        txt-31-2 "- первичная поверка"
  );setq
);if

;//////////////////////////////////////////////////
(if (= txt-32 "Обыкновенная")                  
  (setq txt-32-1 ""
        txt-32-2 "- обычная точность"
  );setq
);if

(if (= txt-32 "Повышенная")                  
  (setq txt-32-1 "/HAC"
        txt-32-2 "- повышенная точность"
  );setq
);if

;//////////////////////////////////////////////////
(if (= txt-33 "Обычное, IP67")                  
  (setq txt-33-1 ""
        txt-33-2 "- без взрывозащиты, IP67"
  );setq
);if

(if (= txt-33 "0ExiaIICT5X")
  (setq txt-33-1 "/KS2"
        txt-33-2 "- 0ExiaIICT5X (искробезопасная цепь)"
  );setq
);if

(if (= txt-33 "1ExdIICT4...T6")
  (setq txt-33-1 "/KF2"
        txt-33-2 "- 1ExdIICT4...T6 (взрывонепроницаемая оболочка)"
  );setq
);if

(setq txt-ins-1 (strcat "EJA310A" txt-15-1 txt-16-1 txt-17-1 txt-18-1 txt-21-1 txt-22-1 txt-23-1 txt-24-1 txt-25-1 txt-31-1 txt-32-1 txt-33-1)
      ;txt-ins-2 (strcat txt-22-1 txt-23-1 txt-24-1 txt-25-1 txt-31-1 txt-32-1 txt-33-1)
);setq

;отрисовка строк спецификации
(101-empt-lin-spcf)
(setvar "osmode" 6199)
(setq pnt-ins		(getpoint "\nУкажите точку вставки\n")
	    x-pnt-ins (nth 0 pnt-ins)
	    y-pnt-ins (nth 1 pnt-ins)
	    ypnt-ins-1 y-pnt-ins
);setq



(setvar "osmode" 0)
(setvar "cmdecho" 0)

(repeat num-lin
  (command "_insert" "зс-пустая-строка" "_X" 1 "_Y" 1 "_Z" 1 "_R" 0 (list x-pnt-ins ypnt-ins-1))
  (setq ypnt-ins-1 (- ypnt-ins-1 8)
  );setq
);repeat

(command "_TEXT" "_ML" (list (+ x-pnt-ins 1) (- y-pnt-ins 4)) 2.5 0 "Датчик абсолютного давления");наименование

(command "_TEXT" "_ML" (list (+ x-pnt-ins 5) (- y-pnt-ins 12)) 2.5 0 (strcat "- измеряемая среда " (strcase txt-10 4)))
(command "_TEXT" "_ML" (list (+ x-pnt-ins 5) (- y-pnt-ins 20)) 2.5 0 (strcat "- температура измеряемой среды " txt-11 "..." txt-12 " %%dC"))
(command "_TEXT" "_ML" (list (+ x-pnt-ins 5) (- y-pnt-ins 28)) 2.5 0 (strcat "- температура окружающей среды " txt-13 "..." txt-14 " %%dC"))
(command "_TEXT" "_ML" (list (+ x-pnt-ins 5) (- y-pnt-ins 36)) 2.5 0 (strcat txt-15-2))
(command "_TEXT" "_ML" (list (+ x-pnt-ins 5) (- y-pnt-ins 44)) 2.5 0 (strcat txt-16-2))
(command "_TEXT" "_ML" (list (+ x-pnt-ins 5) (- y-pnt-ins 52)) 2.5 0 (strcat txt-16-3))
(command "_TEXT" "_ML" (list (+ x-pnt-ins 5) (- y-pnt-ins 60)) 2.5 0 (strcat txt-18-2))
(command "_TEXT" "_ML" (list (+ x-pnt-ins 5) (- y-pnt-ins 68)) 2.5 0 (strcat txt-18-3))
(command "_TEXT" "_ML" (list (+ x-pnt-ins 5) (- y-pnt-ins 76)) 2.5 0 (strcat txt-21-2))
(command "_TEXT" "_ML" (list (+ x-pnt-ins 5) (- y-pnt-ins 84)) 2.5 0 (strcat txt-22-2))
(command "_TEXT" "_ML" (list (+ x-pnt-ins 5) (- y-pnt-ins 92)) 2.5 0 (strcat txt-22-3))
(command "_TEXT" "_ML" (list (+ x-pnt-ins 5) (- y-pnt-ins 100)) 2.5 0 (strcat txt-23-2))
(command "_TEXT" "_ML" (list (+ x-pnt-ins 5) (- y-pnt-ins 108)) 2.5 0 (strcat txt-24-2))
(command "_TEXT" "_ML" (list (+ x-pnt-ins 5) (- y-pnt-ins 116)) 2.5 0 (strcat txt-25-2))
(command "_TEXT" "_ML" (list (+ x-pnt-ins 5) (- y-pnt-ins 124)) 2.5 0 (strcat "- государственная поверка"))
(command "_TEXT" "_ML" (list (+ x-pnt-ins 5) (- y-pnt-ins 132)) 2.5 0 (strcat txt-32-2))
(command "_TEXT" "_ML" (list (+ x-pnt-ins 5) (- y-pnt-ins 140)) 2.5 0 (strcat txt-33-2))
(command "_TEXT" "_ML" (list (+ x-pnt-ins 5) (- y-pnt-ins 148)) 2.5 0 (strcat "- требуемый диапазон измерений " txt-19 "..." txt-110 " кгс/см2"))

(command "_TEXT" "_MC" (list (+ x-pnt-ins 160) (- y-pnt-ins 4)) 2.5 0 txt-ins-1);код заказа
;(command "_TEXT" "_MC" (list (+ x-pnt-ins 160) (- y-pnt-ins 12)) 2.5 0 txt-ins-2)

(command "_TEXT" "_MC" (list (+ x-pnt-ins 280) (- y-pnt-ins 4)) 2.5 0 "шт.");количество

(command "_TEXT" "_MC" (list (+ x-pnt-ins 247.5) (- y-pnt-ins 4)) 2.5 0 "\"ЭТАЛОН-ПРИБОР\",");производитель
(command "_TEXT" "_MC" (list (+ x-pnt-ins 247.5) (- y-pnt-ins 12)) 2.5 0 "г. Челябинск")

(command "_text" "_MC" (list (+ x-pnt-ins 322.5) (- y-pnt-ins 4)) 2.5 0 "4")

(command "_TEXT" "_ML" (list (+ x-pnt-ins 336) (- y-pnt-ins 4)) 2.5 0 "№14495-09 в Госреестре");сертификат
(command "_TEXT" "_ML" (list (+ x-pnt-ins 336) (- y-pnt-ins 12)) 2.5 0 "средств измерений,")
(command "_TEXT" "_ML" (list (+ x-pnt-ins 336) (- y-pnt-ins 20)) 2.5 0 "свидетельство")
(command "_TEXT" "_ML" (list (+ x-pnt-ins 336) (- y-pnt-ins 28)) 2.5 0 "об утверждении типа")
(command "_TEXT" "_ML" (list (+ x-pnt-ins 336) (- y-pnt-ins 36)) 2.5 0 "средств измерений")
(command "_TEXT" "_ML" (list (+ x-pnt-ins 336) (- y-pnt-ins 44)) 2.5 0 "JP.C.30.004.A №38504")
(command "_TEXT" "_ML" (list (+ x-pnt-ins 336) (- y-pnt-ins 52)) 2.5 0 "от 15.03.2010г.,")
(command "_TEXT" "_ML" (list (+ x-pnt-ins 336) (- y-pnt-ins 60)) 2.5 0 "разрешение")
(command "_TEXT" "_ML" (list (+ x-pnt-ins 336) (- y-pnt-ins 68)) 2.5 0 "Ростехнадзора")
(command "_TEXT" "_ML" (list (+ x-pnt-ins 336) (- y-pnt-ins 76)) 2.5 0 "на применение")
(command "_TEXT" "_ML" (list (+ x-pnt-ins 336) (- y-pnt-ins 84)) 2.5 0 "№ РРС 00-32124")
(command "_TEXT" "_ML" (list (+ x-pnt-ins 336) (- y-pnt-ins 92)) 2.5 0 "от 24.11.2008г.")

(setvar "osmode" 6199)
(setvar "cmdecho" 1)
(vla-endundomark adoc)
(princ)
)
;/////// конец программы ///////

;///////////////////////////////////////////////////////////////////////////////////////////////////////////////
;///////////////////////////////////////////////////////////////////////////////////////////////////////////////
;///////////////////////////////////////////////////////////////////////////////////////////////////////////////
(defun list-filling
(name-list data-list / )

(progn
  (start_list name-list)
  (mapcar 'add_list data-list)
  (end_list)
);progn

(princ)
)
;///////////////////////////////////////////////////////////////////////////////////////////////////////////////
;///////////////////////////////////////////////////////////////////////////////////////////////////////////////
;///////////////////////////////////////////////////////////////////////////////////////////////////////////////

;///////////////////////////////////////////////////////////////////////////////////////////////////////////////
;///////////////////////////////////////////////////////////////////////////////////////////////////////////////
;///////////////////////////////////////////////////////////////////////////////////////////////////////////////
(defun tmp-1-101-eja310a-etalon
(/ model-1)

(setq model-1 (nth (atoi (get_tile "txt-15")) list-15)
);setq

(if (= "FOUNDATION Fieldbus" model-1)
  (setq list-33 (list "Обычное, IP67")
  );setq
);if

(if (/= "FOUNDATION Fieldbus" model-1)
  (setq list-33 (list "Обычное, IP67" "0ExiaIICT5X" "1ExdIICT4...T6")
  );setq
);if

(list-filling "txt-33" list-33)
(set_tile "txt-33" "0")

(princ)
)
;///////////////////////////////////////////////////////////////////////////////////////////////////////////////
;///////////////////////////////////////////////////////////////////////////////////////////////////////////////
;///////////////////////////////////////////////////////////////////////////////////////////////////////////////

;///////////////////////////////////////////////////////////////////////////////////////////////////////////////
;///////////////////////////////////////////////////////////////////////////////////////////////////////////////
;///////////////////////////////////////////////////////////////////////////////////////////////////////////////
(defun tmp-2-101-eja530a-etalon
($value / type-1)

(setq type-1 (nth (atoi $value) list-17)
);setq

(if (= "0...50 МПа (5...50)" type-1)
  (setq list-18 (list "0,12")
  );setq
);if

(if (/= "0...50 МПа (5...50)" type-1)
  (setq list-18 (list "0,2" "0,075")
  );setq
);if

(list-filling "txt-18" list-18)
(set_tile "txt-18" "0")

(princ)
)
;///////////////////////////////////////////////////////////////////////////////////////////////////////////////
;///////////////////////////////////////////////////////////////////////////////////////////////////////////////
;///////////////////////////////////////////////////////////////////////////////////////////////////////////////
