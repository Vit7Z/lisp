;/////// ************************************************************ ///////////////////////////////////////////////////////////////////////////////////////////////////////////
;///////                                                              ///////////////////////////////////////////////////////////////////////////////////////////////////////////
;/////// ************************************************************ ///////////////////////////////////////////////////////////////////////////////////////////////////////////
(defun 101-01-tmprt-sens-tpt1

( / adoc counter dcl-id list-01 list-02 list-03 list-04 list-05 list-06 list-07 list-08 list-901 list-902 str-01 str-f type-list)

(vl-load-com)
(vla-startundomark (setq adoc (vla-get-activedocument (vlax-get-acad-object))));start undo

(setq str-f 1
      counter 0
      list-01 (list "ТПТ-1-1" "ТПТ-1-2" "ТПТ-1-3" "ТПТ-1-4" "ТПТ-1-5" "ТМТ-1-1" "ТМТ-1-2" "ТМТ-1-3" "ТМТ-1-4" "ТМТ-1-5")
			list-02 nil
			list-03 nil
			list-04 nil
			list-05 nil
			list-06 nil
			list-07 nil
			list-08 nil
			list-901 nil
			list-902 nil
			str-01 nil
);setq

(start-101-01-tmprt-sens-tpt1)

(if (< (setq dcl-id (load_dialog "dia-101-01-tmprt-sens-tpt1.dcl")) 0) ;ищем диалог
		(progn
			(alert "Не найден dcl-файл")
			(exit)
		);progn
);if

(if (not (new_dialog "dia_tpt_1" dcl-id))
		(exit)
);if

(list-filling "txt-01" list-01)
(list-filling "txt-02" list-02)
(list-filling "txt-03" list-03)
(list-filling "txt-04" list-04)
(list-filling "txt-05" list-05)
(list-filling "txt-06" list-06)
(list-filling "txt-07" list-07)
(list-filling "txt-08" list-08)

(set_tile "txt-01" "0")
(set_tile "txt-02" "0")
(set_tile "txt-03" "0")
(set_tile "txt-04" "0")
(set_tile "txt-05" "0")
(set_tile "txt-06" "0")
(set_tile "txt-07" "0")
(set_tile "txt-08" "0")

(action_tile "txt-01" ;выбор
  (strcat "(start-101-01-tmprt-sens-tpt1)"
  );strcat
);action_tile

(action_tile "txt-02" ;выбор
  (strcat "(txt-02-101-01-tmprt-sens-tpt1)");strcat
);action_tile

(action_tile "txt-03" ;выбор
  (strcat "(txt-03-101-01-tmprt-sens-tpt1)");strcat
);action_tile

(action_tile "txt-04" ;выбор
  (strcat "(txt-04-101-01-tmprt-sens-tpt1)");strcat
);action_tile

(action_tile "but1"
  (strcat "(tmp-filling-fields-101-01-tmprt-sens-tpt1)");strcat
);action_tile

(action_tile "but2"
  (strcat "(setq type-list \"le\")"
          "(done_dialog)"
  );strcat
);action_tile

(action_tile "but3"
  (strcat "(setq type-list \"spcf\")"
          "(done_dialog)"
  );strcat
);action_tile

(action_tile "but5"
  (strcat "(delete-item)");strcat
);action_tile

(action_tile "accept"
  (strcat "(done_dialog)"
          "(exit)"
  );strcat
);action_tile

(start_dialog)
(unload_dialog dcl-id)

(if (= type-list "le") (le-101-01-tmprt-sens-tpt1));if

(if (= type-list "spcf") (spcf-101-01-tmprt-sens-tpt1));if

(setvar "osmode" 6199)
(setvar "cmdecho" 1)
(vla-endundomark adoc)
(princ)
)
;;;;/////////////////////////////////////////////////////////////////////////////////////////////////////////////////////////////////////////////////////////////////////////////
;/////// конец программы ////////////////////////////////////////////////////////////////////////////////////////////////////////////////////////////////////////////////////////
;;;;/////////////////////////////////////////////////////////////////////////////////////////////////////////////////////////////////////////////////////////////////////////////



;;;;/////////////////////////////////////////////////////////////////////////////////////////////////////////////////////////////////////////////////////////////////////////////
;;;;/////////////////////////////////////////////////////////////////////////////////////////////////////////////////////////////////////////////////////////////////////////////
(defun start-101-01-tmprt-sens-tpt1

()

(if (= nil str-01) 
	(setq str-01 "ТПТ-1-1");setq
	(setq str-01 (nth (atoi (get_tile "txt-01")) list-01));setq
);if

(cond
	((= str-01 "ТПТ-1-1")
		(progn
			(setq list-02 (list "-50...+250" "-100...+450" "-100...+300" "-196...+500" "-196...+300" "0...+150" "-50...+300")
      			list-03 (list "50П" "100П" "500П" "1000П")
      			list-04 (list "АА")
      			list-05 (list "3" "4")
      			list-06 (list "100" "120" "160" "200" "250" "320" "400" "500" "630" "800" "1000" "1250" "1600" "2000" "2500" "3150")
      			list-07 (list "10")
      			list-08 (list "Да")
			);setq
			(set_tile "ptxt-061" "")			
		);progn
	);=

	((= str-01 "ТПТ-1-2")
		(progn
			(setq list-02 (list "-50...+250" "-100...+450" "-100...+300" "-196...+500" "-196...+300" "0...+150" "-50...+300")
      			list-03 (list "50П" "100П" "500П" "1000П")
      			list-04 (list "АА")
      			list-05 (list "3" "4")
      			list-06 (list "200" "250" "320" "500" "630" "800" "1000" "1250" "1600" "2000")
      			list-07 (list "10")
      			list-08 (list "Нет")
			);setq
			(set_tile "ptxt-061" "")			
		);progn
	);=

	((= str-01 "ТПТ-1-3")
		(progn
			(setq list-02 (list "-50...+250" "-100...+450" "-100...+300" "-196...+500" "-196...+300" "0...+150" "-50...+300")
      			list-03 (list "50П" "100П" "500П" "1000П")
      			list-04 (list "АА")
      			list-05 (list "3" "4")
      			list-06 (list "60" "80" "100" "120" "160" "200" "250" "320" "400")
      			list-07 (list "8")
      			list-08 (list "Да")
			);setq
			(set_tile "ptxt-061" "")			
		);progn
	);=

	((= str-01 "ТПТ-1-4")
		(progn
			(setq list-02 (list "-50...+250" "-100...+450" "-100...+300" "-196...+500" "-196...+300" "0...+150" "-50...+300")
      			list-03 (list "50П" "100П" "500П" "1000П")
      			list-04 (list "АА")
      			list-05 (list "3" "4")
      			list-06 (list "60" "80" "100" "120" "160" "200" "250" "320" "400")
      			list-07 (list "6" "8")
      			list-08 (list "Да")
			);setq
			(set_tile "ptxt-061" "")			
		);progn
	);=

	((= str-01 "ТПТ-1-5")
		(progn
			(setq list-02 (list "-50...+250" "-100...+450" "-100...+300" "-196...+500" "-196...+300" "0...+150" "-50...+300")
      			list-03 (list "50П" "100П" "500П" "1000П")
      			list-04 (list "АА")
      			list-05 (list "3" "4")
      			list-06 (list "200" "250" "320" "400" "500" "630" "800" "1000" "1250" "1600" "2000")
      			list-07 (list "8")
      			list-08 (list "Нет")
			);setq
			(set_tile "ptxt-061" "")			
		);progn
	);=

	((= str-01 "ТМТ-1-1")
		(progn
			(setq list-02 (list "-50...+120" "-50...+200")
      			list-03 (list "50М" "100М")
      			list-04 (list "А")
      			list-05 (list "3" "4")
      			list-06 (list "100" "120" "160" "200" "250" "320" "400" "500" "630" "800" "1000" "1250" "1600" "2000" "2500" "3150")
      			list-07 (list "10")
      			list-08 (list "Да")
			);setq
			(set_tile "ptxt-061" "")			
		);progn
	);=

	((= str-01 "ТМТ-1-2")
		(progn
			(setq list-02 (list "-50...+120" "-50...+200")
      			list-03 (list "50М" "100М")
      			list-04 (list "А")
      			list-05 (list "3" "4")
      			list-06 (list "200" "250" "320" "400" "500" "630" "800" "1000" "1250" "1600" "2000")
      			list-07 (list "10")
      			list-08 (list "Нет")
			);setq
			(set_tile "ptxt-061" "")			
		);progn
	);=

	((= str-01 "ТМТ-1-3")
		(progn
			(setq list-02 (list "-50...+120" "-50...+200")
      			list-03 (list "50М" "100М")
      			list-04 (list "А")
      			list-05 (list "3" "4")
      			list-06 (list "60" "80" "100")
      			list-07 (list "6")
      			list-08 (list "Да")
			);setq
			(set_tile "ptxt-061" "")			
		);progn
	);=

	((= str-01 "ТМТ-1-4")
		(progn
			(setq list-02 (list "-50...+120" "-50...+200")
      			list-03 (list "50П" "100П" "500П" "1000П")
      			list-04 (list "А")
      			list-05 (list "3" "4")
      			list-06 (list "60" "80" "100" "120" "160" "200" "250" "320" "400")
      			list-07 (list "6" "8")
      			list-08 (list "Да")
			);setq
			(set_tile "ptxt-061" "")			
		);progn
	);=

	((= str-01 "ТМТ-1-5")
		(progn
			(setq list-02 (list "-50...+120" "-50...+200")
      			list-03 (list "50П" "100П" "500П" "1000П")
      			list-04 (list "А")
      			list-05 (list "3" "4")
      			list-06 (list "200" "250" "320" "400" "500" "630" "800" "1000" "1250" "1600" "2000")
      			list-07 (list "8")
      			list-08 (list "Нет")
			);setq
			(set_tile "ptxt-061" "")			
		);progn
	);=
); cond

(list-filling "txt-02" list-02)
(list-filling "txt-03" list-03)
(list-filling "txt-04" list-04)
(list-filling "txt-05" list-05)
(list-filling "txt-06" list-06)
(list-filling "txt-07" list-07)
(list-filling "txt-08" list-08)

(set_tile "txt-02" "0")
(set_tile "txt-03" "0")
(set_tile "txt-04" "0")
(set_tile "txt-05" "0")
(set_tile "txt-06" "0")
(set_tile "txt-07" "0")
(set_tile "txt-08" "0")

(princ)
)
;;;;/////////////////////////////////////////////////////////////////////////////////////////////////////////////////////////////////////////////////////////////////////////////
;;;;/////////////////////////////////////////////////////////////////////////////////////////////////////////////////////////////////////////////////////////////////////////////

;////////////////////////////////////////////////////////////////////////////////////////////////////////////////////////////////////////////////////////////////////////////////
;////////////////////////////////////////////////////////////////////////////////////////////////////////////////////////////////////////////////////////////////////////////////
(defun txt-02-101-01-tmprt-sens-tpt1

( / str-01 str-02)

(setq str-01 (nth (atoi (get_tile "txt-01")) list-01)
			str-02 (nth (atoi (get_tile "txt-02")) list-02)
);setq

(if (= str-01 "ТПТ-1-1")
	(cond
		((= "-50...+250" str-02) (setq list-03 (list "50П" "100П" "500П" "1000П") list-04 (list "АА") list-05 (list "3" "4")));=
		((= "-100...+450" str-02) (setq list-03 (list "50П" "100П" "500П" "1000П") list-04 (list "А") list-05 (list "3" "4")));=
		((= "-100...+300" str-02) (setq list-03 (list "50П" "100П" "500П" "1000П") list-04 (list "А") list-05 (list "3" "4")));=
		((= "-196...+500" str-02) (setq list-03 (list "50П" "100П" "500П" "1000П") list-04 (list "В" "С") list-05 (list "1" "2" "3" "4")));=
		((= "-196...+300" str-02) (setq list-03 (list "50П" "100П" "500П" "1000П") list-04 (list "В" "С") list-05 (list "1" "2" "3" "4")));=
		((= "0...+150" str-02) (setq list-03 (list "Pt100" "Pt500" "Pt1000") list-04 (list "АА") list-05 (list "3" "4")));=
		((= "-50...+300" str-02) (setq list-03 (list "Pt100" "Pt500" "Pt1000") list-04 (list "АА" "А" "В" "С") list-05 (list "3" "4")));=
	);cond
);if

(if (= str-01 "ТПТ-1-2")
	(cond
		((= "-50...+250" str-02) (setq list-03 (list "50П" "100П" "500П" "1000П") list-04 (list "АА") list-05 (list "3" "4")));=
		((= "-100...+450" str-02) (setq list-03 (list "50П" "100П" "500П" "1000П") list-04 (list "А") list-05 (list "3" "4")));=
		((= "-100...+300" str-02) (setq list-03 (list "50П" "100П" "500П" "1000П") list-04 (list "А") list-05 (list "3" "4")));=
		((= "-196...+500" str-02) (setq list-03 (list "50П" "100П" "500П" "1000П") list-04 (list "В" "С") list-05 (list "1" "2" "3" "4")));=
		((= "-196...+300" str-02) (setq list-03 (list "50П" "100П" "500П" "1000П") list-04 (list "В" "С") list-05 (list "1" "2" "3" "4")));=
		((= "0...+150" str-02) (setq list-03 (list "Pt100" "Pt500" "Pt1000") list-04 (list "АА") list-05 (list "3" "4")));=
		((= "-50...+300" str-02) (setq list-03 (list "Pt100" "Pt500" "Pt1000") list-04 (list "АА" "А" "В" "С") list-05 (list "3" "4")));=
	);cond
);if

(if (= str-01 "ТПТ-1-3")
	(cond
		((= "-50...+250" str-02) (setq list-03 (list "50П" "100П" "500П" "1000П") list-04 (list "АА") list-05 (list "3" "4")));=
		((= "-100...+450" str-02) (setq list-03 (list "50П" "100П" "500П" "1000П") list-04 (list "А") list-05 (list "3" "4")));=
		((= "-100...+300" str-02) (setq list-03 (list "50П" "100П" "500П" "1000П") list-04 (list "А") list-05 (list "3" "4")));=
		((= "-196...+500" str-02) (setq list-03 (list "50П" "100П" "500П" "1000П") list-04 (list "В" "С") list-05 (list "1" "2" "3" "4")));=
		((= "-196...+300" str-02) (setq list-03 (list "50П" "100П" "500П" "1000П") list-04 (list "В" "С") list-05 (list "3" "4")));=
		((= "0...+150" str-02) (setq list-03 (list "Pt100" "Pt500" "Pt1000") list-04 (list "АА") list-05 (list "3" "4")));=
		((= "-50...+300" str-02) (setq list-03 (list "Pt100" "Pt500" "Pt1000") list-04 (list "АА" "А" "В" "С") list-05 (list "3" "4")));=
	);cond
);if

(if (= str-01 "ТПТ-1-4")
	(cond
		((= "-50...+250" str-02) (setq list-03 (list "50П" "100П" "500П" "1000П") list-04 (list "АА") list-05 (list "3" "4")));=
		((= "-100...+450" str-02) (setq list-03 (list "50П" "100П" "500П" "1000П") list-04 (list "А") list-05 (list "3" "4")));=
		((= "-100...+300" str-02) (setq list-03 (list "50П" "100П" "500П" "1000П") list-04 (list "А") list-05 (list "3" "4")));=
		((= "-196...+500" str-02) (setq list-03 (list "50П" "100П" "500П" "1000П") list-04 (list "В" "С") list-05 (list "1" "2" "3" "4")));=
		((= "-196...+300" str-02) (setq list-03 (list "50П" "100П" "500П" "1000П") list-04 (list "В" "С") list-05 (list "3" "4")));=
		((= "0...+150" str-02) (setq list-03 (list "Pt100" "Pt500" "Pt1000") list-04 (list "АА") list-05 (list "3" "4")));=
		((= "-50...+300" str-02) (setq list-03 (list "Pt100" "Pt500" "Pt1000") list-04 (list "АА" "А" "В" "С") list-05 (list "3" "4")));=
	);cond
);if

(if (= str-01 "ТПТ-1-5")
	(cond
		((= "-50...+250" str-02) (setq list-03 (list "50П" "100П" "500П" "1000П") list-04 (list "АА") list-05 (list "3" "4")));=
		((= "-100...+450" str-02) (setq list-03 (list "50П" "100П" "500П" "1000П") list-04 (list "А") list-05 (list "3" "4")));=
		((= "-100...+300" str-02) (setq list-03 (list "50П" "100П" "500П" "1000П") list-04 (list "А") list-05 (list "3" "4")));=
		((= "-196...+500" str-02) (setq list-03 (list "50П" "100П" "500П" "1000П") list-04 (list "В" "С") list-05 (list "1" "2" "3" "4")));=
		((= "-196...+300" str-02) (setq list-03 (list "50П" "100П" "500П" "1000П") list-04 (list "В" "С") list-05 (list "3" "4")));=
		((= "0...+150" str-02) (setq list-03 (list "Pt100" "Pt500" "Pt1000") list-04 (list "АА") list-05 (list "3" "4")));=
		((= "-50...+300" str-02) (setq list-03 (list "Pt100" "Pt500" "Pt1000") list-04 (list "АА" "А") list-05 (list "3" "4")));=
	);cond
);if

(if (= str-01 "ТМТ-1-1")
	(cond
		((= "-50...+120" str-02) (setq list-04 (list "А") list-05 (list "3" "4")));=
		((= "-50...+200" str-02) (setq list-04 (list "В" "С") list-05 (list "1" "2" "3" "4")));=
	);cond
);if

(if (= str-01 "ТМТ-1-2")
	(cond
		((= "-50...+120" str-02) (setq list-04 (list "А") list-05 (list "3" "4")));=
		((= "-50...+200" str-02) (setq list-04 (list "В" "С") list-05 (list "1" "2" "3" "4")));=
	);cond
);if

(if (= str-01 "ТМТ-1-3")
	(cond
		((= "-50...+120" str-02) (setq list-04 (list "А") list-05 (list "3" "4")));=
		((= "-50...+200" str-02) (setq list-04 (list "В" "С") list-05 (list "1" "2" "3" "4")));=
	);cond
);if

(if (= str-01 "ТМТ-1-4")
	(cond
		((= "-50...+120" str-02) (setq list-04 (list "А") list-05 (list "3" "4")));=
		((= "-50...+200" str-02) (setq list-04 (list "В" "С") list-05 (list "1" "2" "3" "4")));=
	);cond
);if

(if (= str-01 "ТМТ-1-5")
	(cond
		((= "-50...+120" str-02) (setq list-04 (list "А") list-05 (list "3" "4")));=
		((= "-50...+200" str-02) (setq list-04 (list "В" "С") list-05 (list "1" "2" "3" "4")));=
	);cond
);if

(list-filling "txt-03" list-03)
(list-filling "txt-04" list-04)
(list-filling "txt-05" list-05)

(set_tile "txt-03" "0")
(set_tile "txt-04" "0")
(set_tile "txt-05" "0")

(princ)
)
;////////////////////////////////////////////////////////////////////////////////////////////////////////////////////////////////////////////////////////////////////////////////
;////////////////////////////////////////////////////////////////////////////////////////////////////////////////////////////////////////////////////////////////////////////////

;////////////////////////////////////////////////////////////////////////////////////////////////////////////////////////////////////////////////////////////////////////////////
;////////////////////////////////////////////////////////////////////////////////////////////////////////////////////////////////////////////////////////////////////////////////
(defun txt-03-101-01-tmprt-sens-tpt1

( / str-01 str-03)

(setq str-01 (nth (atoi (get_tile "txt-01")) list-01)
			str-03 (nth (atoi (get_tile "txt-03")) list-03)
);setq

(if (= str-01 "ТПТ-1-3")
	(cond
		((= "500П" str-03) (setq list-06 (list "100" "120" "160" "200" "250" "320" "400")));=
		((= "1000П" str-03) (setq list-06 (list "100" "120" "160" "200" "250" "320" "400")));=
		(T (setq list-06 (list "60" "80" "100" "120" "160" "200" "250" "320" "400")));=
	);cond
);if

(if (= str-01 "ТПТ-1-4")
	(cond
		((= "500П" str-03) (setq list-06 (list "100" "120" "160" "200" "250" "320" "400")));=
		((= "1000П" str-03) (setq list-06 (list "100" "120" "160" "200" "250" "320" "400")));=
		(T (setq list-06 (list "60" "80" "100" "120" "160" "200" "250" "320" "400")));=
	);cond
);if

(list-filling "txt-06" list-06)

(set_tile "txt-06" "0")

(princ)
)
;////////////////////////////////////////////////////////////////////////////////////////////////////////////////////////////////////////////////////////////////////////////////
;////////////////////////////////////////////////////////////////////////////////////////////////////////////////////////////////////////////////////////////////////////////////

;////////////////////////////////////////////////////////////////////////////////////////////////////////////////////////////////////////////////////////////////////////////////
;////////////////////////////////////////////////////////////////////////////////////////////////////////////////////////////////////////////////////////////////////////////////
(defun txt-04-101-01-tmprt-sens-tpt1

( / str-02 str-04)

(setq str-02 (nth (atoi (get_tile "txt-02")) list-02)
			str-04 (nth (atoi (get_tile "txt-04")) list-04)
);setq

(if (= str-02 "-50...+300")
	(cond
		((= "В" str-04) (setq list-05 (list "1" "2" "3" "4")));=
		((= "С" str-04) (setq list-05 (list "1" "2" "3" "4")));=
		(T (setq list-05 (list "3" "4")));=
	);cond
);if

(list-filling "txt-05" list-05)
(set_tile "txt-05" "0")

(princ)
)
;////////////////////////////////////////////////////////////////////////////////////////////////////////////////////////////////////////////////////////////////////////////////
;////////////////////////////////////////////////////////////////////////////////////////////////////////////////////////////////////////////////////////////////////////////////


;;;;/////////////////////////////////////////////////////////////////////////////////////////////////////////////////////////////////////////////////////////////////////////////
;;;;подпрограмма формирования данных/////////////////////////////////////////////////////////////////////////////////////////////////////////////////////////////////////////////
(defun tmp-filling-fields-101-01-tmprt-sens-tpt1

( / cntr-1 str-01 str-02 str-03 str-04 str-05 str-06 str-07 str-08 str-902 str-99)

;заполняем поле "выбрано"
(setq str-01 (nth (atoi (get_tile "txt-01")) list-01)
			str-02 (nth (atoi (get_tile "txt-02")) list-02)
			str-03 (nth (atoi (get_tile "txt-03")) list-03)
			str-04 (nth (atoi (get_tile "txt-04")) list-04)
			str-05 (nth (atoi (get_tile "txt-05")) list-05)
			str-06 (nth (atoi (get_tile "txt-06")) list-06)
			str-07 (nth (atoi (get_tile "txt-07")) list-07)
			str-08 (nth (atoi (get_tile "txt-08")) list-08)
      cntr-1 0 ;счетчик, номер элемента в списке
);setq

(if (/= list-901 nil)
	(setq list-902 (reverse list-902)
				list-901 (reverse list-901)
	);setq
);if

(setq str-99
	(cond	
		((= str-06 "60") "0,2")
		((= str-06 "80") "0,2")
		((= str-06 "100") "0,2");=
		((= str-06 "120") "0,2");=
		((= str-06 "160") "0,2");=
		((= str-06 "200") "0,2");=
		((= str-06 "250") "0,3");=
		((= str-06 "320") "0,5");=
		((= str-06 "400") "0,6");=
		((= str-06 "500") "0,7");=
		((= str-06 "630") "0,8");=
		((= str-06 "800") "0,9");=
		((= str-06 "1000") "0,9");=
		((= str-06 "1250") "1,1");=
		((= str-06 "1600") "1,5");=
		((= str-06 "2000") "1,2");=
		((= str-06 "2500") "1,2");=
		((= str-06 "3150") "1,3");=
	);cond
);setq

(setq str-902 (list (cons 1 str-01) (cons 2 str-02) (cons 3 str-03) (cons 4 str-04) (cons 5 str-05) (cons 6 str-06) (cons 7 str-07)	(cons 8 str-08) (cons 99 str-99))
  		list-902 (vl-list*  str-902 list-902);список характеристик для спецификации
  		list-901 (vl-list* (strcat str-01 "  " 
  															 str-02 "  " 
  															 "НСХ" str-03 "  " 
  															 "Класс допуска "str-04 "  " 
  															 "Сх. соед." str-05 "  " 
  															 "Длина " str-06 "  " 
  															 "Диаметр монт. части " str-07 "мм.  " 
  															 "Штуцер приварн. " str-08) list-901)
);setq

(setq list-902 (reverse list-902)
			list-901 (reverse list-901)
);setq

(list-filling "txt-901" list-901)

(princ)
)
;;;;/////////////////////////////////////////////////////////////////////////////////////////////////////////////////////////////////////////////////////////////////////////////
;;;;/////////////////////////////////////////////////////////////////////////////////////////////////////////////////////////////////////////////////////////////////////////////


;;;;/////////////////////////////////////////////////////////////////////////////////////////////////////////////////////////////////////////////////////////////////////////////
;;;;подпрограмма вывода в ПЭ                   //////////////////////////////////////////////////////////////////////////////////////////////////////////////////////////////////
(defun le-101-01-tmprt-sens-tpt1

( / cntr-1 dlt-y nmbr-ln pnt-ins tmp tmp-1 tmp-11 tmp-2 tmp-6 x-pnt-ins y-pnt-ins y-pnt-ins-1)

(setq cntr-1 0);setq

(repeat (length list-902)
	(setq tmp (nth cntr-1 list-902)
				tmp-1 (cdr (assoc 1 tmp))
				tmp-2 (cdr (assoc 2 tmp))
				tmp-6 (cdr (assoc 6 tmp))
	);setq



	(setq tmp-11 (substr tmp-1 1 (vl-string-search "-" tmp-1)));setq

	(cond
		((= "ТПТ" tmp-11) (setq tmp-11 "из платины "));=
		((= "ТМТ" tmp-11) (setq tmp-11 "из меди "));=
	);cond

	(setvar "osmode" 6199)
	
	(setq pnt-ins		(getpoint "\nУкажите точку вставки\n")
  			x-pnt-ins (nth 0 pnt-ins)
 				y-pnt-ins (nth 1 pnt-ins)
  			y-pnt-ins-1 y-pnt-ins
  			dlt-y 8
	);setq
	
	(100-empt-lin-le)

	(setq nmbr-ln 3);setq
	
	(1000-delete-items-le nmbr-ln x-pnt-ins y-pnt-ins)
	
	(command "_text" "_ML" (list (+ x-pnt-ins 1) (- (- y-pnt-ins (* dlt-y 0)) 4)) 2.5 0 (strcat "Термометр технический " tmp-11 tmp-1 ", предел. изм"))
	(command "_text" "_ML" (list (+ x-pnt-ins 1) (- (- y-pnt-ins (* dlt-y 1)) 4)) 2.5 0 (strcat tmp-2 "%%dС, Lпогр. " tmp-6 "мм, диаметр монтажной части "))
;	(command "_text" "_ML" (list (+ x-pnt-ins 1) (- (- y-pnt-ins (* dlt-y 1)) 4)) 2.5 0 (strcat "Lпогр. " tmp-6 "мм."))

	(setq cntr-1 (1+ cntr-1));setq
);repeat

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;подпрограмма вывода в спцф                   ////////////////////////////////////////////////////////////////////////////////////////////////////////////////////////////////

(defun spcf-101-01-tmprt-sens-tpt1

( / cntr-1 dlt-y dt-2-03 dt-8-01 nmbr-ln pnt-ins tmp tmp-1 tmp-11 tmp-2 tmp-3 tmp-4 tmp-5 tmp-6 tmp-7 tmp-8 tmp-8-1 tmp-99 x-pnt-ins y-pnt-ins y-pnt-ins-1)

(setq cntr-1 0);setq

(setvar "textstyle" "Standard")

(repeat (length list-902)
	(setq tmp (nth cntr-1 list-902)
				tmp-1 (cdr (assoc 1 tmp))
				tmp-2 (cdr (assoc 2 tmp))
				tmp-3 (cdr (assoc 3 tmp))
				tmp-4 (cdr (assoc 4 tmp))
				tmp-5 (cdr (assoc 5 tmp))
				tmp-6 (cdr (assoc 6 tmp))
				tmp-7 (cdr (assoc 7 tmp))
				tmp-8 (cdr (assoc 8 tmp))
				tmp-99 (cdr (assoc 99 tmp))
	);setq
	
	(setvar "osmode" 6199)
	(setq pnt-ins		(getpoint "\nУкажите точку вставки\n")
	  		x-pnt-ins (nth 0 pnt-ins)
	 			y-pnt-ins (nth 1 pnt-ins)
	  		y-pnt-ins-1 y-pnt-ins
	  		dlt-y 8
	);setq
	
	(101-empt-lin-spcf)
	
	;обработка данных
	(setq tmp-11 (substr tmp-1 1 (vl-string-search "-" tmp-1)));setq
	
	(cond
		((= "ТПТ" tmp-11) 
			(setq tmp-11 "из платины"
						dt-2-03 "ТУ 4211-010-17113168-10"
						dt-8-01 "№46155-10"
			);setq
		);=
		((= "ТМТ" tmp-11) 
			(setq tmp-11 "из меди"
						dt-2-03 "ТУ 4211-080-17113168-06"
						dt-8-01 "№15422-06"
			);setq
		);=
	);cond
	
	(cond	
		((= tmp-8 "Да") (setq tmp-8-1 "с приварным штуцером"));=
		((= tmp-8 "Нет") (setq tmp-8-1 "без приварного штуцера"));=
	);cond

	(setq nmbr-ln 5);setq
	
	(1000-delete-items-spcf nmbr-ln x-pnt-ins y-pnt-ins);удаление предыдущей записи
	(1000-delete-items-spcf-crtf nmbr-ln x-pnt-ins y-pnt-ins);удаление предыдущего сертификата
	
	(command "_text" "_ML" (list (+ x-pnt-ins 1) (- (- y-pnt-ins (* dlt-y 0)) 4)) 2.5 0 (strcat "Термометр технический " tmp-11))
	(command "_text" "_ML" (list (+ x-pnt-ins 5) (- (- y-pnt-ins (* dlt-y 1)) 4)) 2.5 0 (strcat "- диапазон измеряемых температур " tmp-2 " %%dC, монтажная длина " tmp-6 " мм"))
	(command "_text" "_ML" (list (+ x-pnt-ins 5) (- (- y-pnt-ins (* dlt-y 2)) 4)) 2.5 0 (strcat "- НСХ " tmp-3 ", класс допуска " tmp-4 ", схема соединения с ЧЭ № " tmp-5))
	(command "_text" "_ML" (list (+ x-pnt-ins 5) (- (- y-pnt-ins (* dlt-y 3)) 4)) 2.5 0 (strcat "- диаметр монтажной части " tmp-7 " мм, " tmp-8-1))
	;
	(command "_TEXT" "_MC" (list (+ x-pnt-ins 160) (- (- y-pnt-ins (* dlt-y 0)) 4)) 2.5 0 (strcat tmp-1 "-" tmp-3 "-" tmp-4 "-")) ;Тип, марка, обозначение документа, опросного листа
	(command "_text" "_MC" (list (+ x-pnt-ins 160) (- (- y-pnt-ins (* dlt-y 1)) 4)) 2.5 0 (strcat tmp-5 "-(" tmp-2 ")-" tmp-6))
	(command "_text" "_MC" (list (+ x-pnt-ins 160) (- (- y-pnt-ins (* dlt-y 2)) 4)) 2.5 0 dt-2-03)
	;
	(command "_text" "_ML" (list (+ x-pnt-ins 336) (- (- y-pnt-ins (* dlt-y 0)) 4)) 2.5 0 dt-8-01)
	(command "_text" "_ML" (list (+ x-pnt-ins 336) (- (- y-pnt-ins (* dlt-y 1)) 4)) 2.5 0 (strcat "в Госреестре СИ"))

	(command "_text" "_MC" (list (+ x-pnt-ins 247.5) (- (- y-pnt-ins (* dlt-y 0)) 4)) 2.5 0 "ЗАО \"Термико\",")
	(command "_text" "_MC" (list (+ x-pnt-ins 247.5) (- (- y-pnt-ins (* dlt-y 1)) 4)) 2.5 0 "г. Москва, Зеленоград")	

	(command "_text" "_MC" (list (+ x-pnt-ins 280) (- (- y-pnt-ins (* dlt-y 0)) 4)) 2.5 0 "шт.")
			
	(command "_text" "_MC" (list (+ x-pnt-ins 322.5) (- (- y-pnt-ins (* dlt-y 0)) 4)) 2.5 0 tmp-99);масса
	
	(repeat nmbr-ln
  	(command "_insert" "зс-пустая-строка" "_X" 1 "_Y" 1 "_Z" 1 "_R" 0 (list x-pnt-ins y-pnt-ins-1))
  	(setq y-pnt-ins-1 (- y-pnt-ins-1 8));setq
	);repeat
 
	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////
