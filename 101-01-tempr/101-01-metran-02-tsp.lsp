;/////// ************************************************************ ///////////////////////////////////////////////////////////////////////////////////////////////////////////
;///////                                                              ///////////////////////////////////////////////////////////////////////////////////////////////////////////
;/////// ************************************************************ ///////////////////////////////////////////////////////////////////////////////////////////////////////////
(defun 101-01-tempr-metran-02-tsp

( / adoc counter dcl-id list-01 list-02 list-03 list-04 list-05 list-06 list-07 list-08 list-09 list-10 list-11 list-12 list-13 list-901 list-902 str-01 str-f type-list)

(vl-load-com)
(vla-startundomark
  (setq adoc (vla-get-activedocument (vlax-get-acad-object)));setq
);start undo

(setq str-f 1
			str-01 nil
      counter 0
      list-01 (list "ТСП Метран-206")
      list-901 nil
      list-902 nil
);setq

(strt-101-01-tmprt-sensr-metran-tsp)

(if (< (setq dcl-id (load_dialog "dia-101-01-tempr-metran-02-tsp.dcl")) 0) ;ищем диалог
		(progn
			(alert "Не найден dcl-файл")
			(exit)
		);progn
);if

(if (not (new_dialog "dia_101_01_tempr_metran_02_tsp" dcl-id))
		(exit)
);if

(list-filling "txt-01" list-01)
(list-filling "txt-02" list-02)
(list-filling "txt-03" list-03)
(list-filling "txt-04" list-04)
(list-filling "txt-05" list-05)
(list-filling "txt-06" list-06)
(list-filling "txt-07" list-07)
(list-filling "txt-08" list-08)
(list-filling "txt-09" list-09)
(list-filling "txt-10" list-10)
(list-filling "txt-11" list-11)
(list-filling "txt-12" list-12)
(list-filling "txt-13" list-13)

(set_tile "txt-01" "0")
(set_tile "txt-02" "0")
(set_tile "txt-03" "0")
(set_tile "txt-04" "0")
(set_tile "txt-05" "0")
(set_tile "txt-06" "0")
(set_tile "txt-07" "0")
(set_tile "txt-08" "0")
(set_tile "txt-09" "0")
(set_tile "txt-10" "0")
(set_tile "txt-11" "0")
(set_tile "txt-12" "0")
(set_tile "txt-13" "0")


(action_tile "txt-01"
  (strcat "(strt-101-01-tmprt-sensr-metran-tsp)");srcat
);action_tile

(action_tile "txt-02"
  (strcat "(txt-02-101-01-tmprt-sensr-metran-tsp)"
  );srcat
);action_tile

(action_tile "txt-04"
  (strcat "(txt-04-101-01-tmprt-sensr-metran-tsp)"
  );srcat
);action_tile

(action_tile "txt-06"
  (strcat "(txt-06-101-01-tmprt-sensr-metran-tsp)"
  );srcat
);action_tile

(action_tile "txt-07"
  (strcat "(txt-07-101-01-tmprt-sensr-metran-tsp)"
  );srcat
);action_tile

(action_tile "but1"
  (strcat "(tmp-filling-fields-101-01-tmprt-sensr-metran-tsp)"
  );strcat
);action_tile

(action_tile "but2"
  (strcat "(setq type-list \"le\")"
          "(done_dialog)"
  );strcat
);action_tile

(action_tile "but3"
  (strcat "(setq type-list \"spcf\")"
          "(done_dialog)"
  );strcat
);action_tile

(action_tile "accept"
  (strcat "(done_dialog)"
          "(exit)"
  );strcat
);action_tile

;для диалога выбора длины погружения
(action_tile "txt-21"
  (strcat "(tmp-21-101-temp-sensor-telokontr-kaz)"
  );strcat
);action_tile

(action_tile "txt-22"
  (strcat "(tmp-22-101-temp-sensor-telokontr-kaz)"
  );strcat
);action_tile

(action_tile "txt-23"
  (strcat "(tmp-22-101-temp-sensor-telokontr-kaz)"
  				"(tmp-23-101-temp-sensor-telokontr-kaz)"
  );strcat
);action_tile

(start_dialog)
(unload_dialog dcl-id)

(cond
	((= type-list "le") (le-101-01-tmprt-sensr-metran-tsp));=
	((= type-list "spcf") (spcf-101-01-tmprt-sensr-metran-tsp));=
);cond

(setvar "osmode" 6199)
(setvar "cmdecho" 1)
(vla-endundomark adoc)
(princ)
)
;;;;/////////////////////////////////////////////////////////////////////////////////////////////////////////////////////////////////////////////////////////////////////////////
;/////// конец программы ////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun strt-101-01-tmprt-sensr-metran-tsp

( / )

(if (= nil str-01) 
	(setq str-01 "ТСП Метран-206");setq
	(setq str-01 (nth (atoi (get_tile "txt-01")) list-01));setq
);if

(if (= "ТСП Метран-206" str-01)
	(progn
		(setq list-02 (list "01 (без штуцера)" "02 (штуцер подвижн.)" "03 (штуцер подвижн.)" "31 (без штуцера)" "32 (штуцер подвижн.)" "33 (штуцер подвижн.)" "04 (без штуцера)" );"06 (штуцер подвижн.)" "07 (штуцер подвижн.)"
					list-03 (list "Полиамид" "Полиамид" "Полиамид" "Алюмин. сплав" "Алюмин. сплав" "Алюмин. сплав"  "Пластик" "Полиамид" "Алюмин. сплав")
					list-04 (list "-50...+200" "-50...+500" "-200...+500")
					list-05 (list "B")
					list-06 (list "2" "3" "4")
					list-07 (list "1" "2")
					list-08 (list "160" "200" "250" "320" "400" "500" "630" "800" "1000" "1250" "1600" "2000")
					list-09 (list "12Х18Н10Т" "10Х17Н13М2Т")
					list-10 (list "У1.1 (-50...+80)" "Т3 (-10...+70)")
					list-11 (list "10")
					list-12 (list "100П")
					list-13 (list "Нет")
		);setq
		(set_tile "ptxt-01" "Для измерения температуры жидких и газообразных химически неагрессивных сред, а также агрессивных, не разрушающих материал защитной арматуры")
	);progn
);if


(list-filling "txt-02" list-02)
(list-filling "txt-03" list-03)
(list-filling "txt-04" list-04)
(list-filling "txt-05" list-05)
(list-filling "txt-06" list-06)
(list-filling "txt-07" list-07)
(list-filling "txt-08" list-08)
(list-filling "txt-09" list-09)
(list-filling "txt-10" list-10)
(list-filling "txt-11" list-11)
(list-filling "txt-12" list-12)
(list-filling "txt-13" list-13)

(set_tile "txt-02" "0")
(set_tile "txt-03" "0")
(set_tile "txt-04" "0")
(set_tile "txt-05" "0")
(set_tile "txt-06" "0")
(set_tile "txt-07" "0")
(set_tile "txt-08" "0")
(set_tile "txt-09" "0")
(set_tile "txt-10" "0")
(set_tile "txt-11" "0")
(set_tile "txt-12" "0")
(set_tile "txt-13" "0")

(princ)
)
;;;;/////////////////////////////////////////////////////////////////////////////////////////////////////////////////////////////////////////////////////////////////////////////
;;;;/////////////////////////////////////////////////////////////////////////////////////////////////////////////////////////////////////////////////////////////////////////////

;////////////////////////////////////////////////////////////////////////////////////////////////////////////////////////////////////////////////////////////////////////////////
;////////////////////////////////////////////////////////////////////////////////////////////////////////////////////////////////////////////////////////////////////////////////
(defun txt-02-101-01-tmprt-sensr-metran-tsp

( / str-01 str-02 str-02-1)

(setq str-01 (nth (atoi (get_tile "txt-01")) list-01)
			str-02 (nth (atoi (get_tile "txt-02")) list-02)
			str-02-1 (get_tile "txt-02")
);setq

(set_tile "txt-03" str-02-1)

(if (= str-01 "ТСП Метран-206")
	(cond
		((or (= "01 (без штуцера)" str-02)
				 (= "31 (без штуцера)" str-02));or
    	(setq list-04 (list "-50...+200" "-50...+500" "-200...+500")
    				list-05 (list "B")
						list-06 (list "2" "3" "4")
						list-07 (list "1" "2")
						list-08 (list "160" "200" "250" "320" "400" "500" "630" "800" "1000" "1250" "1600" "2000")
						list-09 (list "12Х18Н10Т" "10Х17Н13М2Т")
						list-10 (list "У1.1 (-50...+80)" "Т3 (-10...+70)")
						list-11 (list "10")
						list-13 (list "Нет")    	
    	);setq
    	(set_tile "ptxt-01" "Для измерения температуры жидких и газообразных химически неагрессивных сред, а также агрессивных, не разрушающих материал защитной арматуры")
		);=

		((or (= "02 (штуцер подвижн.)" str-02)
				 (= "32 (штуцер подвижн.)" str-02));or
			(setq list-04 (list "-50...+200" "-50...+500" "-200...+500")
						list-05 (list "B")
						list-06 (list "2" "3" "4")
						list-07 (list "1" "2")
						list-08 (list "60" "80" "100" "120" "160" "200" "250" "320" "400" "500" "630" "800" "1000" "1250" "1600" "2000" "2500" "3150")
						list-09 (list "12Х18Н10Т" "10Х17Н13М2Т")
						list-10 (list "У1.1 (-50...+80)" "Т3 (-10...+70)")
						list-11 (list "10")
						list-13 (list "Нет")
   		);setq
   		(set_tile "ptxt-01" "Для измерения температуры жидких и газообразных химически неагрессивных сред, а также агрессивных, не разрушающих материал защитной арматуры")
		);=

		((or (= "03 (штуцер подвижн.)" str-02)
				 (= "33 (штуцер подвижн.)" str-02));or
			(setq list-04 (list "-50...+200" "-50...+500" "-200...+500")
						list-05 (list "B" )
						list-06 (list "2" "3" "4")
						list-07 (list "1" "2")
						list-08 (list "100" "120" "160" "200" "250" "320" "400" "500" "630" "800" "1000" "1250")
						list-09 (list "12Х18Н10Т" "10Х17Н13М2Т")
						list-10 (list "У1.1 (-50...+80)" "Т3 (-10...+70)")
						list-11 (list "8")
						list-13 (list "Нет")
   		);setq
   		(set_tile "ptxt-01" "Для измерения температуры жидких и газообразных химически неагрессивных сред, а также агрессивных, не разрушающих материал защитной арматуры")
		);=

		((= "04 (без штуцера)" str-02)
    	(setq list-04 (list "-50...+150")
    				list-05 (list "B" "C")
    				list-06 (list "4")
    				list-07 (list "1")
    				list-08 (list "100")
    				list-09 (list "12Х18Н10Т")
    				list-10 (list "У1.1 (-50...+85)" "Т3 (-10...+70)")
					  list-11 (list "8")
					 	list-13 (list "Нет")
    	);setq
    	(set_tile "ptxt-01" "Для измерения температуры воздуха в помещениях различного назначения")
		);=

		((or (= "06 (штуцер подвижн.)" str-02)
				 (= "07 (штуцер подвижн.)" str-02));or
    	(setq list-04 (list "-50...+200" "-50...+500" "-200...+500")
						list-05 (list "B")
						list-06 (list "2" "3" "4")
						list-07 (list "1" "2")
						list-08 (list "60" "80" "100" "120" "160" "200" "250" "320" "400" "500" "630" "800")
						list-09 (list "12Х18Н10Т" "10Х17Н13М2Т")
						list-10 (list "У1.1 (-50...+80)" "Т3 (-10...+70)")
						list-11 (list "10")
						list-10 (list "У1.1 (-50...+80)" "Т3 (-10...+70)")
						list-13 (list "G3/4")
    	);setq
    	(set_tile "ptxt-01" "Для измерения температуры жидких и газообразных химически неагрессивных сред, а также агрессивных, не разрушающих материал защитной арматуры")
		);=
	);cond
);if

(list-filling "txt-04" list-04)
(list-filling "txt-05" list-05)
(list-filling "txt-06" list-06)
(list-filling "txt-07" list-07)
(list-filling "txt-08" list-08)
(list-filling "txt-09" list-09)
(list-filling "txt-10" list-10)
(list-filling "txt-11" list-11)
(list-filling "txt-13" list-13)

(set_tile "txt-04" "0")
(set_tile "txt-05" "0")
(set_tile "txt-06" "0")
(set_tile "txt-07" "0")
(set_tile "txt-08" "0")
(set_tile "txt-09" "0")
(set_tile "txt-10" "0")
(set_tile "txt-11" "0")
(set_tile "txt-13" "0")

(princ)
)
;////////////////////////////////////////////////////////////////////////////////////////////////////////////////////////////////////////////////////////////////////////////////
;////////////////////////////////////////////////////////////////////////////////////////////////////////////////////////////////////////////////////////////////////////////////

;////////////////////////////////////////////////////////////////////////////////////////////////////////////////////////////////////////////////////////////////////////////////
;////////////////////////////////////////////////////////////////////////////////////////////////////////////////////////////////////////////////////////////////////////////////
(defun txt-04-101-01-tmprt-sensr-metran-tsp

( / str-01 str-02 str-04)

(setq str-01 (nth (atoi (get_tile "txt-01")) list-01)
			str-02 (nth (atoi (get_tile "txt-02")) list-02)
			str-04 (nth (atoi (get_tile "txt-04")) list-04)
);setq


(if (and (= str-01 "ТСП Метран-206") (or (= "01 (без штуцера)" str-02) (= "31 (без штуцера)" str-02)));and
	(cond
		((= "-50...+200" str-04)
			(setq list-05 (list "B")
						list-06 (list "2" "3" "4")
						list-07 (list "1" "2")
						list-08 (list "160" "200" "250" "320" "400" "500" "630" "800" "1000" "1250" "1600" "2000")
			);setq
		);=
			 
		((= "-50...+500" str-04) 
			(setq list-05 (list "A")
						list-06 (list "3" "4")
						list-07 (list "1")
						list-08 (list "160" "200" "250" "320" "400" "500" "630" "800" "1000" "1250" "1600" "2000")
  		);setq
		);=

		((= "-200...+500" str-04) 
			(setq list-05 (list "B")
						list-06 (list "2")
						list-07 (list "1")
						list-08 (list "120" "160")
  		);setq
		);=
	);cond
);if

(if (and (= str-01 "ТСП Метран-206") (or (= "02 (штуцер подвижн.)" str-02) (= "32 (штуцер подвижн.)" str-02)));and
	(cond
		((= "-50...+200" str-04)
			(setq list-05 (list "B")
						list-06 (list "2" "3" "4")
						list-07 (list "1")
						list-08 (list "60" "80" "100" "120" "160" "200" "250" "320" "400" "500" "630" "800" "1000" "1250" "1600" "2000" "2500" "3150")
			);setq
		);=
			 
		((= "-50...+500" str-04) 
			(setq list-05 (list "A")
						list-06 (list "3" "4")
						list-07 (list "1")
						list-08 (list "60" "80" "100" "120" "160" "200" "250" "320" "400" "500" "630" "800" "1000" "1250" "1600" "2000" "2500" "3150")
  		);setq
		);=

		((= "-200...+500" str-04) 
			(setq list-05 (list "B")
						list-06 (list "3" "4")
						list-07 (list "1")
						list-08 (list "60" "80" "100" "120" "160" "200" "250" "320" "400" "500" "630" "800" "1000" "1250" "1600" "2000" "2500" "3150")
  		);setq
		);=
	);cond
);if

(if (and (= str-01 "ТСП Метран-206") (or (= "03 (штуцер подвижн.)" str-02) (= "33 (штуцер подвижн.)" str-02)));and
	(cond
		((= "-50...+200" str-04)
			(setq list-05 (list "B")
						list-06 (list "2" "3" "4")
						list-07 (list "1")
						list-08 (list "100" "120" "160" "200" "250" "320" "400" "500" "630" "800" "1000" "1250")
			);setq
		);=
			 
		((= "-50...+500" str-04) 
			(setq list-05 (list "A")
						list-06 (list "3" "4")
						list-07 (list "1")
						list-08 (list "100" "120" "160" "200" "250" "320" "400" "500" "630" "800" "1000" "1250" "1600" "2000" "2500" "3150")
  		);setq
		);=

		((= "-200...+500" str-04) 
			(setq list-05 (list "B")
						list-06 (list "3" "4")
						list-07 (list "1")
						list-08 (list "100" "120" "160" "200" "250" "320" "400" "500" "630" "800" "1000" "1250" "1600" "2000" "2500" "3150")
  		);setq
		);=
	);cond
);if

(if (and (= str-01 "ТСП Метран-206") (= "04 (без штуцера)" str-02));and
	(setq list-05 (list "B" "C")
    		list-06 (list "4")
    		list-07 (list "1")
    		list-08 (list "100")
  );setq
);if

(if (and (= str-01 "ТСП Метран-206") (or (= "06 (штуцер подвижн.)" str-02) (= "07 (штуцер подвижн.)" str-02)));and
	(cond
		((= "-50...+200" str-04)
			(setq list-05 (list "B")
						list-06 (list "2" "3" "4")
						list-07 (list "1")
						list-08 (list "60" "80" "100" "120" "180" "200" "250" "320" "400" "500" "630" "800")
			);setq
		);=
			 
		((= "-50...+500" str-04) 
			(setq list-05 (list "A")
						list-06 (list "3" "4")
						list-07 (list "1")
						list-08 (list "60" "80" "100" "120" "160" "200" "250" "320" "400" "500" "630" "800" "1000" "1250" "1600" "2000" "2500" "3150")
  		);setq
		);=

		((= "-200...+500" str-04) 
			(setq list-05 (list "B")
						list-06 (list "2" "3" "4")
						list-07 (list "1")
						list-08 (list "60" "80" "100" "120" "160" "200")
  		);setq
		);=
	);cond
);if


(list-filling "txt-05" list-05)
(list-filling "txt-06" list-06)
(list-filling "txt-07" list-07)
(list-filling "txt-08" list-08)

(set_tile "txt-05" "0")
(set_tile "txt-06" "0")
(set_tile "txt-07" "0")
(set_tile "txt-08" "0")

(princ)
)
;////////////////////////////////////////////////////////////////////////////////////////////////////////////////////////////////////////////////////////////////////////////////
;////////////////////////////////////////////////////////////////////////////////////////////////////////////////////////////////////////////////////////////////////////////////


;////////////////////////////////////////////////////////////////////////////////////////////////////////////////////////////////////////////////////////////////////////////////
;////////////////////////////////////////////////////////////////////////////////////////////////////////////////////////////////////////////////////////////////////////////////
(defun txt-06-101-01-tmprt-sensr-metran-tsp

( / str-01 str-02 str-04 str-05 str-06)

(setq str-01 (nth (atoi (get_tile "txt-01")) list-01)
			str-02 (nth (atoi (get_tile "txt-02")) list-02)
			str-04 (nth (atoi (get_tile "txt-04")) list-04)
			str-05 (nth (atoi (get_tile "txt-05")) list-05)
			str-06 (nth (atoi (get_tile "txt-06")) list-06)
);setq

;;;;////////////////////////////////////////////////////////////////////////////////////////////////////////////////////
(if (and (= str-01 "ТСП Метран-206") (or (= "01 (без штуцера)" str-02) (= "31 (без штуцера)" str-02)) (= "-50...+200" str-04) (= "B" str-05));and
	(cond
		((= "2" str-06) (setq list-07 (list "1" "2") list-08 (list "160" "200" "250" "320" "400" "500" "630" "800" "1000" "1250" "1600" "2000")));=
		((= "3" str-06) (setq list-07 (list "2") list-08 (list "160" "200" "250" "320" "400" "500" "630" "800" "1000" "1250" "1600" "2000")));=
		((= "4" str-06) (setq list-07 (list "1") list-08 (list "160" "200" "250" "320" "400" "500" "630" "800" "1000" "1250" "1600" "2000")));=
	);cond
);if

(if (and (= str-01 "ТСП Метран-206") (or (= "01 (без штуцера)" str-02) (= "31 (без штуцера)" str-02)) (= "-50...+500" str-04) (= "A" str-05));and
	(cond
		((= "3" str-06) (setq list-07 (list "1") list-08 (list "160" "200" "250" "320" "400" "500" "630" "800" "1000" "1250" "1600" "2000")));=
		((= "4" str-06) (setq list-07 (list "1") list-08 (list "160" "200" "250" "320" "400" "500" "630" "800" "1000" "1250" "1600" "2000")));=
	);cond
);if

(if (and (= str-01 "ТСП Метран-206") (or (= "01 (без штуцера)" str-02) (= "31 (без штуцера)" str-02)) (= "-200...+500" str-04) (= "B" str-05));and
	(cond
		((= "2" str-06) (setq list-07 (list "1") list-08 (list "120" "160")));=
		((= "3" str-06) (setq list-07 (list "1") list-08 (list "160" "200" "250" "320" "400" "500" "630" "800" "1000" "1250" "1600" "2000")));=
		((= "4" str-06) (setq list-07 (list "1") list-08 (list "160" "200" "250" "320" "400" "500" "630" "800" "1000" "1250" "1600" "2000")));=
	);cond
);if

;;;;////////////////////////////////////////////////////////////////////////////////////////////////////////////////////
(if (and (= str-01 "ТСП Метран-206") (or (= "02 (штуцер подвижн.)" str-02) (= "32 (штуцер подвижн.)" str-02)) (= "-50...+200" str-04) (= "B" str-05));and
	(cond
		((= "2" str-06) (setq list-07 (list "1" "2") list-08 (list "60" "80" "100" "120" "160" "200" "250" "320" "400" "500" "630" "800" "1000" "1250" "1600" "2000" "2500" "3150")));=
		((= "3" str-06) (setq list-07 (list "2") list-08 (list "60" "80" "100" "120" "160" "200" "250" "320" "400" "500" "630" "800" "1000" "1250" "1600" "2000" "2500" "3150")));=
		((= "4" str-06) (setq list-07 (list "1") list-08 (list "160" "200" "250" "320" "400" "500" "630" "800" "1000" "1250")));=
	);cond
);if

(if (and (= str-01 "ТСП Метран-206") (or (= "02 (штуцер подвижн.)" str-02) (= "32 (штуцер подвижн.)" str-02)) (= "-50...+500" str-04) (= "A" str-05));and
	(cond
		((or (= "3" str-06) (= "4" str-06)) (setq list-07 (list "1") list-08 (list "60" "80" "100" "120" "160" "200" "250" "320" "400" "500" "630" "800" "1000" "1250" "1600" "2000" "2500" "3150")));=
	);cond
);if

(if (and (= str-01 "ТСП Метран-206") (or (= "02 (штуцер подвижн.)" str-02) (= "32 (штуцер подвижн.)" str-02)) (= "-200...+500" str-04) (= "B" str-05));and
	(cond
		((or (= "3" str-06) (= "4" str-06)) (setq list-07 (list "1") list-08 (list "60" "80" "100" "120" "160" "200" "250" "320" "400" "500" "630" "800" "1000" "1250" "1600" "2000" "2500" "3150")));=
	);cond
);if

;;;;////////////////////////////////////////////////////////////////////////////////////////////////////////////////////
(if (and (= str-01 "ТСП Метран-206") (or (= "03 (штуцер подвижн.)" str-02) (= "33 (штуцер подвижн.)" str-02)) (= "-50...+200" str-04) (= "B" str-05));and
	(cond
		((= "2" str-06) (setq list-07 (list "1" "2") list-08 (list "100" "120" "160" "200" "250" "320" "400" "500" "630" "800" "1000" "1250")));=
		((= "3" str-06) (setq list-07 (list "2") list-08 (list "100" "120" "160" "200" "250" "320" "400" "500" "630" "800" "1000" "1250")));=
		((= "4" str-06) (setq list-07 (list "1") list-08 (list "100" "120" "160" "200" "250" "320" "400" "500" "630" "800" "1000" "1250")));=
	);cond
);if

(if (and (= str-01 "ТСП Метран-206") (or (= "03 (штуцер подвижн.)" str-02) (= "33 (штуцер подвижн.)" str-02)) (= "-50...+500" str-04) (= "A" str-05));and
	(cond
		((or (= "3" str-06) (= "4" str-06)) (setq list-07 (list "1") list-08 (list "100" "120" "160" "200" "250" "320" "400" "500" "630" "800" "1000" "1250" "1600" "2000" "2500" "3150")));=
	);cond
);if

(if (and (= str-01 "ТСП Метран-206") (or (= "03 (штуцер подвижн.)" str-02) (= "33 (штуцер подвижн.)" str-02)) (= "-200...+500" str-04) (= "B" str-05));and
	(cond
		((or (= "3" str-06) (= "4" str-06)) (setq list-07 (list "1") list-08 (list "100" "120" "160" "200" "250" "320" "400" "500" "630" "800" "1000" "1250" "1600" "2000" "2500" "3150")));=
	);cond
);if

(list-filling "txt-07" list-07)
(list-filling "txt-08" list-08)

(set_tile "txt-07" "0")
(set_tile "txt-08" "0")

(princ)
)
;////////////////////////////////////////////////////////////////////////////////////////////////////////////////////////////////////////////////////////////////////////////////
;////////////////////////////////////////////////////////////////////////////////////////////////////////////////////////////////////////////////////////////////////////////////


;////////////////////////////////////////////////////////////////////////////////////////////////////////////////////////////////////////////////////////////////////////////////
;////////////////////////////////////////////////////////////////////////////////////////////////////////////////////////////////////////////////////////////////////////////////
(defun txt-07-101-01-tmprt-sensr-metran-tsp

( / str-01 str-02 str-04 str-05 str-06 str-07)

(setq str-01 (nth (atoi (get_tile "txt-01")) list-01)
			str-02 (nth (atoi (get_tile "txt-02")) list-02)
			str-04 (nth (atoi (get_tile "txt-04")) list-04)
			str-05 (nth (atoi (get_tile "txt-05")) list-05)
			str-06 (nth (atoi (get_tile "txt-06")) list-06)
			str-07 (nth (atoi (get_tile "txt-07")) list-07)
);setq

;;;;////////////////////////////////////////////////////////////////////////////////////////////////////////////////////
(if (and (= str-01 "ТСП Метран-206") (or (= "01 (без штуцера)" str-02) (= "31 (без штуцера)" str-02)) (= "-50...+200" str-04) (= "B" str-05));and
	(cond
		((and (or (= "2" str-06) (= "4" str-06)) (= "1" str-07)) 
			(setq list-08 (list "160" "200" "250" "320" "400" "500" "630" "800" "1000" "1250" "1600" "2000"))
		);=
		
		((and (= "3" str-06) (= "2" str-07)) 
			(setq list-08 (list "160" "200" "250" "320" "400" "500" "630" "800" "1000" "1250" "1600" "2000"))
		);=
		
		((and (= "2" str-06) (= "2" str-07)) 
			(setq list-08 (list "160" "200" "250" "320" "400" "500" "630" "800" "1000" "1250"))
		);=
	);cond
);if

(if (and (= str-01 "ТСП Метран-206") (or (= "01 (без штуцера)" str-02) (= "31 (без штуцера)" str-02)) (= "-50...+500" str-04) (= "A" str-05));and
	(cond
		((and (or (= "3" str-06) (= "4" str-06)) (= "1" str-07)) 
			(setq list-08 (list "160" "200" "250" "320" "400" "500" "630" "800" "1000" "1250" "1600" "2000"))
		);=
	);cond
);if

(if (and (= str-01 "ТСП Метран-206") (or (= "01 (без штуцера)" str-02) (= "31 (без штуцера)" str-02)) (= "-200...+500" str-04) (= "B" str-05));and
	(cond
		((and (= "2" str-06) (= "1" str-07)) 
			(setq list-08 (list "120" "160"))
		);=
	
		((and (or (= "3" str-06) (= "4" str-06)) (= "1" str-07)) 
			(setq list-08 (list "160" "200" "250" "320" "400" "500" "630" "800" "1000" "1250" "1600" "2000"))
		);=
	);cond
);if

;;;;////////////////////////////////////////////////////////////////////////////////////////////////////////////////////
(if (and (= str-01 "ТСП Метран-206") (or (= "02 (штуцер подвижн.)" str-02) (= "32 (штуцер подвижн.)" str-02)) (= "-50...+200" str-04) (= "B" str-05));and
	(cond
		((and (or (= "2" str-06) (= "4" str-06)) (= "1" str-07)) 
			(setq list-08 (list "60" "80" "100" "120" "160" "200" "250" "320" "400" "500" "630" "800" "1000" "1250" "1600" "2000" "2500" "3150"))
		);=
		
		((and (= "3" str-06) (= "2" str-07)) 
			(setq list-08 (list "60" "80" "100" "120" "160" "200" "250" "320" "400" "500" "630" "800" "1000" "1250" "1600" "2000" "2500" "3150"))
		);=
		
		((and (= "2" str-06) (= "2" str-07)) 
			(setq list-08 (list "60" "80" "100" "120" "160" "200" "250" "320" "400" "500" "630" "800" "1000" "1250"))
		);=
	);cond
);if

(if (and (= str-01 "ТСП Метран-206") (or (= "02 (штуцер подвижн.)" str-02) (= "32 (штуцер подвижн.)" str-02)) (= "-50...+500" str-04) (= "A" str-05));and
	(cond
		((and (or (= "3" str-06) (= "4" str-06)) (= "1" str-07)) 
			(setq list-08 (list "60" "80" "100" "120" "160" "200" "250" "320" "400" "500" "630" "800" "1000" "1250" "1600" "2000" "2500" "3150"))
		);=
	);cond
);if

(if (and (= str-01 "ТСП Метран-206") (or (= "02 (штуцер подвижн.)" str-02) (= "32 (штуцер подвижн.)" str-02)) (= "-200...+500" str-04) (= "B" str-05));and
	(cond
		((and (or (= "3" str-06) (= "4" str-06)) (= "1" str-07)) 
			(setq list-08 (list "60" "80" "100" "120" "160" "200" "250" "320" "400" "500" "630" "800" "1000" "1250" "1600" "2000" "2500" "3150"))
		);=
	);cond
);if

(list-filling "txt-08" list-08)

(set_tile "txt-08" "0")

(princ)
)
;////////////////////////////////////////////////////////////////////////////////////////////////////////////////////////////////////////////////////////////////////////////////
;////////////////////////////////////////////////////////////////////////////////////////////////////////////////////////////////////////////////////////////////////////////////


;;;;/////////////////////////////////////////////////////////////////////////////////////////////////////////////////////////////////////////////////////////////////////////////
;;;;подпрограмма формирования данных/////////////////////////////////////////////////////////////////////////////////////////////////////////////////////////////////////////////
(defun tmp-filling-fields-101-01-tmprt-sensr-metran-tsp

( / cntr-1 str-01 str-02 str-03 str-04 str-05 str-06 str-07 str-08 str-09 str-10 str-11 str-12 str-13 str-99 swtch)

;заполняем поле "выбрано"
(setq str-01 (nth (atoi (get_tile "txt-01")) list-01)
			str-02 (nth (atoi (get_tile "txt-02")) list-02)
			str-03 (nth (atoi (get_tile "txt-03")) list-03)
			str-04 (nth (atoi (get_tile "txt-04")) list-04)
			str-05 (nth (atoi (get_tile "txt-05")) list-05)
			str-06 (nth (atoi (get_tile "txt-06")) list-06)
			str-07 (nth (atoi (get_tile "txt-07")) list-07)
			str-08 (nth (atoi (get_tile "txt-08")) list-08)
			str-09 (nth (atoi (get_tile "txt-09")) list-09)
			str-10 (nth (atoi (get_tile "txt-10")) list-10)
			str-11 (nth (atoi (get_tile "txt-11")) list-11)
			str-12 (nth (atoi (get_tile "txt-12")) list-12)
			str-13 (nth (atoi (get_tile "txt-13")) list-13)
      swtch list-901
      cntr-1 0
);setq

(if (/= swtch nil) (setq list-902 (reverse list-902)));if

(if (= str-01 "ТСП Метран-206");масса
	(setq str-99
		(cond	
			((and (>= (atoi str-08) 60) (<= (atoi str-08) 120)) "0,5")
			((and (>= (atoi str-08) 160) (<= (atoi str-08) 500)) "0,6")
			((and (>= (atoi str-08) 630) (<= (atoi str-08) 1000)) "0,8")
			((and (>= (atoi str-08) 1250) (<= (atoi str-08) 2000)) "1,1")
			((>= (atoi str-08) 2500) "1,5")
		);cond
	);setq
);if


(setq str-902 (list (cons 1 str-01) (cons 2 str-02) (cons 3 str-03) (cons 4 str-04) (cons 5 str-05) (cons 6 str-06) (cons 7 str-07)	(cons 8 str-08) (cons 9 str-09) 
										(cons 10 str-10) (cons 11 str-11) (cons 12 str-12) (cons 13 str-13) (cons 99 str-99))
  		list-902 (vl-list*  str-902 list-902);список характеристик для спецификации
  		
  		list-901 (vl-list* (strcat str-01 "  " str-02 "  " str-03 "  " str-04 "С  Класс допуска " str-05 "  Схема соединен. " str-06 "-х проводн.  Кол. ЧЭ " str-07 "  Длина " str-08 "мм  " 
  															 str-09 "  " str-10 "  Диам. " str-11 "мм  НСХ " str-12 "  Кабельн. ввод " str-13) list-901)
);setq

(setq list-902 (reverse list-902))

(list-filling "txt-901" (reverse list-901))

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;подпрограмма вывода в ПЭ                   //////////////////////////////////////////////////////////////////////////////////////////////////////////////////////////////////
(defun le-101-01-tmprt-sensr-metran-tsp

( / cntr-1 pnt-ins str-01 str-02 str-04 str-08 str-12 str-701 str-702 str-tmp)

(setq cntr-1 0);setq

(repeat (length list-902)
	(setq str-tmp (nth cntr-1 list-902)
				str-01 (cdr (assoc 1 str-tmp))
				str-02 (cdr (assoc 2 str-tmp))
				str-04 (cdr (assoc 4 str-tmp))
				str-08 (cdr (assoc 8 str-tmp))
				str-12 (cdr (assoc 12 str-tmp))
				
				str-702 nil
	);setq
	
	(setvar "osmode" 6199)
	
	(setq pnt-ins (getpoint "\nУкажите точку вставки\n"));setq
	
	;;;;////////////////////////////////////////////////////////////////////////////////////////////////////////////////////
	(if (and (= str-01 "ТСП Метран-206") (/= str-02 "04 (без штуцера)"))
		(setq str-701 (strcat "Термопреобразователь сопротивления платиновый ТСП Метран-206, пределы измерений " str-04 "%%dС, длина "
													"монтажной части " str-08 "мм, НСХ " str-12)
		);setq
	);if

	(if (and (= str-01 "ТСП Метран-206") (= str-02 "04 (без штуцера)"))
		(setq str-701 (strcat "Термопреобразователь сопротивления платиновый ТСП Метран-206, пределы измерений " str-04 "%%dС, длина "
													"монтажной части " str-08 "мм, НСХ " str-12 ", для измерения температуры воздуха, крепление на плоскость")
		);setq
	);if

	(split-str-parts-le-01-general str-701 str-702 pnt-ins "*22*");

	(setq cntr-1 (1+ cntr-1));setq
);repeat

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;подпрограмма вывода в спцф                   ////////////////////////////////////////////////////////////////////////////////////////////////////////////////////////////////

(defun spcf-101-01-tmprt-sensr-metran-tsp

( / cntr-1 dlt-y nmbr-ln pnt-ins str-01 str-02 str-021 str-022 str-03 str-04 str-05 str-06 str-07 str-08 str-09 str-091 str-10 str-101 str-11 str-12 str-13 str-99 
str-tmp str-txt x-pnt-ins y-pnt-ins y-pnt-ins-1)

(setq cntr-1 0);setq

(setvar "textstyle" "Standard")

(repeat (length list-902)
	(setq str-tmp (nth cntr-1 list-902)
				str-01 (cdr (assoc 1 str-tmp))
				str-02 (cdr (assoc 2 str-tmp))
				str-03 (cdr (assoc 3 str-tmp))
				str-04 (cdr (assoc 4 str-tmp))
				str-05 (cdr (assoc 5 str-tmp))
				str-06 (cdr (assoc 6 str-tmp))
				str-07 (cdr (assoc 7 str-tmp))
				str-08 (cdr (assoc 8 str-tmp))
				str-09 (cdr (assoc 9 str-tmp))
				str-10 (cdr (assoc 10 str-tmp))
				str-11 (cdr (assoc 11 str-tmp))
				str-12 (cdr (assoc 12 str-tmp))
				str-13 (cdr (assoc 13 str-tmp))
				str-99 (cdr (assoc 99 str-tmp))
	);setq
		
	(setvar "osmode" 6199)
	
	(setq pnt-ins (getpoint "\nУкажите точку вставки\n"));setq
	
	(setq str-091
		(cond	
			((= str-09 "12Х18Н10Т") "Н10")
			((= str-09 "10Х17Н13М2Т") "Н13")
		);cond
	);setq
	
	(setq str-101 (substr str-10 1 (vl-string-search " " str-10)));setq
	
	;обработка данных
	;;;;////////////////////////////////////////////////////////////////////////////////////////////////////////////////////
	(if (= str-01 "ТСП Метран-206")
		(if (or (= str-02 "01 (без штуцера)") (= str-02 "02 (штуцер подвижн.)") (= str-02 "03 (штуцер подвижн.)")
						(= str-02 "31 (без штуцера)") (= str-02 "32 (штуцер подвижн.)") (= str-02 "33 (штуцер подвижн.)")
				);or
			(progn
				(cond	
					((= str-02 "01 (без штуцера)") (setq str-021 "по рис. 1 (без штуцера)" str-022 "01"));=
					((= str-02 "02 (штуцер подвижн.)") (setq str-021 "по рис. 2 (штуцер подвижный)" str-022 "02"));=
					((= str-02 "03 (штуцер подвижн.)") (setq str-021 "по рис. 3 (штуцер подвижный)" str-022 "03"));=
					((= str-02 "31 (без штуцера)") (setq str-021 "по рис. 1а (без штуцера)" str-022 "31"));=
					((= str-02 "32 (штуцер подвижн.)") (setq str-021 "по рис. 2а (штуцер подвижный)" str-022 "32"));=
					((= str-02 "33 (штуцер подвижн.)") (setq str-021 "по рис. 3а (штуцер подвижный)" str-022 "33"));=
				);cond
	
				(setq str-03
					(cond	
						((= str-03 "Полиамид") "полиамид")
						((= str-03 "Алюмин. сплав") "алюминиевый сплав")
					);cond
				);setq
	
				(setq nmbr-ln 7);setq
				
				(1000-delete-items-spcf nmbr-ln x-pnt-ins y-pnt-ins)
				(1000-delete-items-spcf-crtf nmbr-ln x-pnt-ins y-pnt-ins)
				
				(command "_text" "_ML" (list (+ x-pnt-ins 1) (- (- y-pnt-ins (* dlt-y 0)) 4)) 2.5 0 "Термопреобразователь сопротивления платиновый")
				(command "_text" "_ML" (list (+ x-pnt-ins 5) (- (- y-pnt-ins (* dlt-y 1)) 4)) 2.5 0 (strcat "- исп. защитной арматуры " str-022 ", длина монтажн. части " str-08 "мм"))
				(command "_text" "_ML" (list (+ x-pnt-ins 5) (- (- y-pnt-ins (* dlt-y 2)) 4)) 2.5 0 (strcat "- схема соединен. " str-06 "-х проводная, материал защитн. арматуры " str-09))
				(command "_text" "_ML" (list (+ x-pnt-ins 5) (- (- y-pnt-ins (* dlt-y 3)) 4)) 2.5 0 (strcat "- пределы изм. " str-04 "%%dC, диаметр термобаллона " str-11 "мм"))
				(command "_text" "_ML" (list (+ x-pnt-ins 5) (- (- y-pnt-ins (* dlt-y 4)) 4)) 2.5 0 (strcat "- климатическое исп. " str-10 "%%dC, НСХ 100П"))
				(command "_text" "_ML" (list (+ x-pnt-ins 5) (- (- y-pnt-ins (* dlt-y 5)) 4)) 2.5 0 (strcat "- материал соединительной головки " str-03))
				;
				(setq str-txt (strcat str-01 "-" str-022 "-" str-08 "-" str-05 "-" str-06 "-" str-07 "-" str-091 "-(" str-04 ")%%dC-" str-101 "-ГП"));setq
				;
				(split-str-parts-spcf-60-01 str-txt "ТУ	4211-002-12580824-2002" pnt-ins)
				;
				(print-number-certificate "№ 47775" pnt-ins)
			);progn
		);if	
	);if	

	;;;;////////////////////////////////////////////////////////////////////////////////////////////////////////////////////
	(if (= str-01 "ТСП Метран-206")
		(if (= str-02 "04 (без штуцера)")
			(progn
				(setq nmbr-ln 7);setq
				
				(1000-delete-items-spcf nmbr-ln x-pnt-ins y-pnt-ins)
				(1000-delete-items-spcf-crtf nmbr-ln x-pnt-ins y-pnt-ins)
				
				(command "_text" "_ML" (list (+ x-pnt-ins 1) (- (- y-pnt-ins (* dlt-y 0)) 4)) 2.5 0 "Термопреобразователь сопротивления платиновый")
				(command "_text" "_ML" (list (+ x-pnt-ins 5) (- (- y-pnt-ins (* dlt-y 1)) 4)) 2.5 0 "- исп. защитной арматуры по рис. 4 (без штуцера)")
				(command "_text" "_ML" (list (+ x-pnt-ins 5) (- (- y-pnt-ins (* dlt-y 2)) 4)) 2.5 0 "- длина монтажной части 100мм. (монтаж на плоскость)")
				(command "_text" "_ML" (list (+ x-pnt-ins 5) (- (- y-pnt-ins (* dlt-y 3)) 4)) 2.5 0 "- схема соединен. 4-х проводная, материал защитн. арматуры 12Х18Н10Т")
				(command "_text" "_ML" (list (+ x-pnt-ins 5) (- (- y-pnt-ins (* dlt-y 4)) 4)) 2.5 0 (strcat "- диаметр термобаллона 8мм, климатическое исполнение " str-101 "%%dC"))
				(command "_text" "_ML" (list (+ x-pnt-ins 5) (- (- y-pnt-ins (* dlt-y 5)) 4)) 2.5 0 "- НСХ 100П, материал соединительной головки пластик")
				;
				(setq str-txt (strcat str-01 "-04-100-" str-05 "-4-1-Н10-(" str-04 ")%%dC-" str-101 "-ГП"));setq
				;
				(split-str-parts-spcf-60-01 str-txt "ТУ	4211-002-12580824-2002" pnt-ins)
				;
				(print-number-certificate "№ 47775" pnt-ins)
			);progn
		);if
	);if

	(command "_text" "_MC" (list (+ x-pnt-ins 322.5) (- (- y-pnt-ins (* dlt-y 0)) 4)) 2.5 0 str-99);масса
	
	(command "_text" "_MC" (list (+ x-pnt-ins 247.5) (- (- y-pnt-ins (* dlt-y 0)) 4)) 2.5 0 "Промышленная группа")
	(command "_text" "_MC" (list (+ x-pnt-ins 247.5) (- (- y-pnt-ins (* dlt-y 1)) 4)) 2.5 0 "\"Метран\",")	
	(command "_text" "_MC" (list (+ x-pnt-ins 247.5) (- (- y-pnt-ins (* dlt-y 2)) 4)) 2.5 0 "г. Челябинск")
	
	(command "_text" "_MC" (list (+ x-pnt-ins 280) (- (- y-pnt-ins (* dlt-y 0)) 4)) 2.5 0 "шт.")
			
	(repeat nmbr-ln
  	(command "_insert" "зс-пустая-строка" "_X" 1 "_Y" 1 "_Z" 1 "_R" 0 (list x-pnt-ins y-pnt-ins-1))
  	(setq y-pnt-ins-1 (- y-pnt-ins-1 8));setq
	);repeat
 
	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////
