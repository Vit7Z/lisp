;/////// ************************************************************ ///////////////////////////////////////////////////////////////////////////////////////////////////////////
;///////                                                              ///////////////////////////////////////////////////////////////////////////////////////////////////////////
;/////// ************************************************************ ///////////////////////////////////////////////////////////////////////////////////////////////////////////
(defun 101-01-tmprt-sens-ttg

( / adoc counter dcl-id list-01 list-02 list-03 list-04 list-05 list-06 list-07 list-901 list-902 str-01 str-f type-list)

(vl-load-com)

(vla-startundomark (setq adoc (vla-get-activedocument (vlax-get-acad-object)))); start undo

(setq str-f 1
      counter 0
      
      list-01 (list "ТТЖ-М исп. 1П")
			list-02 nil
			list-03 nil
			list-04 nil
			list-05 nil
			list-06 nil
			list-07 nil
			
			list-901 nil
			list-902 nil
			
			str-01 nil
);setq

(start-101-01-tmprt-sens-ttg)

(if (< (setq dcl-id (load_dialog "dia-101-01-tmprt-sens-ttg.dcl")) 0) ;ищем диалог
		(progn
			(alert "Не найден dcl-файл")
			(exit)
		);progn
);if

(if (not (new_dialog "dia_101_01_tmprt_sens_ttg" dcl-id))
		(exit)
);if

(list-filling "txt-01" list-01)
(list-filling "txt-02" list-02)
(list-filling "txt-03" list-03)
(list-filling "txt-04" list-04)
(list-filling "txt-05" list-05)
(list-filling "txt-06" list-06)
(list-filling "txt-07" list-07)

(set_tile "txt-01" "0")
(set_tile "txt-02" "0")
(set_tile "txt-03" "0")
(set_tile "txt-04" "0")
(set_tile "txt-05" "0")
(set_tile "txt-06" "0")

(action_tile "txt-01" ;выбор
  (strcat "(start-101-01-tmprt-sens-ttg)");strcat
);action_tile

(action_tile "txt-02" ;выбор
  (strcat "(txt-02-101-01-tmprt-sens-ttg)"
  				"(set_tile \"txt-03\" (get_tile \"txt-02\"))"
  );strcat
);action_tile

(action_tile "txt-03" ;выбор
  (strcat "(set_tile \"txt-02\" (get_tile \"txt-03\"))"
  				"(txt-02-101-01-tmprt-sens-ttg)"
  );strcat
);action_tile

(action_tile "txt-04" ;выбор
  (strcat "(txt-04-101-01-tmprt-sens-ttg)");strcat
);action_tile

(action_tile "but1"
  (strcat "(filling-fields-101-01-tmprt-sens-ttg)");strcat
);action_tile

(action_tile "but2"
  (strcat "(setq type-list \"le\")"
          "(done_dialog)"
  );strcat
);action_tile

(action_tile "but3"
  (strcat "(setq type-list \"spcf\")"
          "(done_dialog)"
  );strcat
);action_tile

(action_tile "but5"
  (strcat "(delete-item)");strcat
);action_tile

(action_tile "accept"
  (strcat "(done_dialog)"
          "(exit)"
  );strcat
);action_tile

(start_dialog)
(unload_dialog dcl-id)

(if (= type-list "le") (le-101-termo-tpt1));if

(if (= type-list "spcf") (spcf-101-termo-tpt1));if

(setvar "osmode" 6199)
(setvar "cmdecho" 1)
(vla-endundomark adoc)
(princ)
)
;;;;/////////////////////////////////////////////////////////////////////////////////////////////////////////////////////////////////////////////////////////////////////////////
;/////// конец программы ////////////////////////////////////////////////////////////////////////////////////////////////////////////////////////////////////////////////////////
;;;;/////////////////////////////////////////////////////////////////////////////////////////////////////////////////////////////////////////////////////////////////////////////



;;;;/////////////////////////////////////////////////////////////////////////////////////////////////////////////////////////////////////////////////////////////////////////////
;;;;/////////////////////////////////////////////////////////////////////////////////////////////////////////////////////////////////////////////////////////////////////////////
(defun start-101-01-tmprt-sens-ttg

()

(if (= nil str-01) 
	(setq str-01 "ТТЖ-М исп. 1П");setq
	(setq str-01 (nth (atoi (get_tile "txt-01")) list-01));setq
);if

(cond
	((= str-01 "ТТЖ-М исп. 1П")
		(progn
			(setq list-02 (list "0...+100" "0...+150")
      			list-03 (list "4" "5")
      			list-04 (list "0,5" "1")
      			list-05 (list "240")
      			list-06 (list "66" "103" "163" "253")
      			list-07 (list "Измерение температуры в технических" 
      										"воздушно-газосиловых установках и"
      										"трубопроводах. Прямой")
			);setq
		);progn
	);=


); cond

(list-filling "txt-02" list-02)
(list-filling "txt-03" list-03)
(list-filling "txt-04" list-04)
(list-filling "txt-05" list-05)
(list-filling "txt-06" list-06)
(list-filling "txt-07" list-07)

(set_tile "txt-02" "0")
(set_tile "txt-03" "0")
(set_tile "txt-04" "0")
(set_tile "txt-05" "0")
(set_tile "txt-06" "0")

(princ)
)
;;;;/////////////////////////////////////////////////////////////////////////////////////////////////////////////////////////////////////////////////////////////////////////////
;;;;/////////////////////////////////////////////////////////////////////////////////////////////////////////////////////////////////////////////////////////////////////////////

;////////////////////////////////////////////////////////////////////////////////////////////////////////////////////////////////////////////////////////////////////////////////
;////////////////////////////////////////////////////////////////////////////////////////////////////////////////////////////////////////////////////////////////////////////////
(defun txt-02-101-01-tmprt-sens-ttg

( / str-01 str-02)

(setq str-01 (nth (atoi (get_tile "txt-01")) list-01)
			str-02 (nth (atoi (get_tile "txt-02")) list-02)
);setq

(if (and (= str-01 "ТТЖ-М исп. 1П") (= "0...+100" str-02))
	(setq list-04 (list "0,5" "1")
      	list-05 (list "240")
      	list-06 (list "66" "103" "163" "253")
	);=
);if

(if (and (= str-01 "ТТЖ-М исп. 1П") (= "0...+150" str-02))
	(setq list-04 (list "1" "2")
      	list-05 (list "240")
      	list-06 (list "66" "103" "163" "253")
	);=
);if

(list-filling "txt-04" list-04)
(list-filling "txt-05" list-05)
(list-filling "txt-06" list-06)

(set_tile "txt-04" "0")
(set_tile "txt-05" "0")
(set_tile "txt-06" "0")

(princ)
)
;////////////////////////////////////////////////////////////////////////////////////////////////////////////////////////////////////////////////////////////////////////////////
;////////////////////////////////////////////////////////////////////////////////////////////////////////////////////////////////////////////////////////////////////////////////


;////////////////////////////////////////////////////////////////////////////////////////////////////////////////////////////////////////////////////////////////////////////////
;////////////////////////////////////////////////////////////////////////////////////////////////////////////////////////////////////////////////////////////////////////////////
(defun txt-04-101-01-tmprt-sens-ttg

( / str-01 str-02 str-04)

(setq str-01 (nth (atoi (get_tile "txt-01")) list-01)
			str-02 (nth (atoi (get_tile "txt-02")) list-02)
			str-04 (nth (atoi (get_tile "txt-04")) list-04)
);setq

(if (and (= str-01 "ТТЖ-М исп. 1П") (= "0...+150" str-02) (= "1" str-04))
	(setq list-05 (list "240")
      	list-06 (list "66" "103" "163" "253")
	);=
);if

(if (and (= str-01 "ТТЖ-М исп. 1П") (= "0...+150" str-02) (= "2" str-04))
	(setq list-05 (list "160" "240")
      	list-06 (list "66" "103" "163" "253" "403" "633" "1003")
	);=
);if

(list-filling "txt-05" list-05)
(list-filling "txt-06" list-06)

(set_tile "txt-05" "0")
(set_tile "txt-06" "0")

(princ)
)
;////////////////////////////////////////////////////////////////////////////////////////////////////////////////////////////////////////////////////////////////////////////////
;////////////////////////////////////////////////////////////////////////////////////////////////////////////////////////////////////////////////////////////////////////////////


;;;;/////////////////////////////////////////////////////////////////////////////////////////////////////////////////////////////////////////////////////////////////////////////
;;;;подпрограмма формирования данных/////////////////////////////////////////////////////////////////////////////////////////////////////////////////////////////////////////////
(defun filling-fields-101-01-tmprt-sens-ttg

( / cntr-1 str-01 str-02 str-03 str-04 str-05 str-06 str-902 str-99 swtch)

;заполняем поле "выбрано"
(setq str-01 (nth (atoi (get_tile "txt-01")) list-01)
			str-02 (nth (atoi (get_tile "txt-02")) list-02)
			str-03 (nth (atoi (get_tile "txt-03")) list-03)
			str-04 (nth (atoi (get_tile "txt-04")) list-04)
			str-05 (nth (atoi (get_tile "txt-05")) list-05)
			str-06 (nth (atoi (get_tile "txt-06")) list-06)
      swtch list-901 ;запоминаем первоначальное состояние списка в поле "выбрано"
      cntr-1 0 ;счетчик, номер элемента в списке
);setq

(if (/= swtch nil);если есть уже выбраннное то переворачиваем
	(setq list-902 (reverse list-902)
				list-901 (reverse list-901)
	);setq
);if

(setq str-99
	(cond	
		((= str-01 "ТТЖ-М исп. 1П") "0,1")
		
		
	);cond
);setq

(if (= str-01 "ТТЖ-М исп. 1П")
	(setq str-902 (list (cons 1 str-01) (cons 2 str-02) (cons 3 str-03) (cons 4 str-04) (cons 5 str-05) (cons 6 str-06) (cons 99 str-99))
				list-902 (vl-list*  str-902 list-902);список характеристик для спецификации
				list-901 (vl-list* (strcat str-01 "  " 
																	 str-02 "°С  " 
																	 "№" str-03 "  " 
																	 "Цена деления " str-04 "°С  " 
																	 "Длина верхней части " str-05 "мм  " 
																	 "Длина нижней части " str-06 "мм") list-901)
	);setq
);if

(if (= swtch nil)
	(setq list-902 (reverse list-902)
				list-901 (reverse list-901)
	);setq
);if

(if (/= swtch nil)
	(setq list-902 (reverse list-902)
				list-901 (reverse list-901)
	);setq
);if

(list-filling "txt-901" list-901)

(princ)
)
;;;;/////////////////////////////////////////////////////////////////////////////////////////////////////////////////////////////////////////////////////////////////////////////
;;;;/////////////////////////////////////////////////////////////////////////////////////////////////////////////////////////////////////////////////////////////////////////////


;;;;/////////////////////////////////////////////////////////////////////////////////////////////////////////////////////////////////////////////////////////////////////////////
;;;;подпрограмма вывода в ПЭ                   //////////////////////////////////////////////////////////////////////////////////////////////////////////////////////////////////
(defun le-101-termo-tpt1

( / cntr-1 str-01 str-txt tmp tmp-1 tmp-2 tmp-4 tmp-5 tmp-6 tmp-99)

(setq cntr-1 0);setq

(repeat (length list-902)
	(setq tmp (nth cntr-1 list-902)
				tmp-1 (cdr (assoc 1 tmp))
				tmp-2 (cdr (assoc 2 tmp))
				tmp-4 (cdr (assoc 4 tmp))
				tmp-5 (cdr (assoc 5 tmp))
				tmp-6 (cdr (assoc 6 tmp))
	);setq

	(setvar "osmode" 6199)
	
	(setq pnt-ins		(getpoint "\nУкажите точку вставки\n"));setq
	
	(100-empt-lin-le)
	
	;///////////////////////////////////////////////////////////////////
	(if (= tmp-1 "ТТЖ-М исп. 1П")
		(setq str-txt (strcat "Термометр технический жидкостной ТТЖ-М, исп. 1, прямой, предел изм. "
													tmp-2 "%%dС, L верхней части " tmp-5 "мм, L нижней части " tmp-6 "мм")
		);setq
	);if

	(split-str-parts-le-110-01 str-txt pnt-ins)

	(setq cntr-1 (1+ cntr-1));setq
);repeat

(princ)
)
;;;;/////////////////////////////////////////////////////////////////////////////////////////////////////////////////////////////////////////////////////////////////////////////
;;;;/////////////////////////////////////////////////////////////////////////////////////////////////////////////////////////////////////////////////////////////////////////////

;;;;/////////////////////////////////////////////////////////////////////////////////////////////////////////////////////////////////////////////////////////////////////////////
;;;;подпрограмма вывода в спцф                   ////////////////////////////////////////////////////////////////////////////////////////////////////////////////////////////////

(defun spcf-101-termo-tpt1

( / cntr-1 dlt-y dt-2-01 dt-2-02 dt-2-03 dt-8-01 nmbr-ln pnt-ins tmp tmp-1 tmp-11 tmp-2 tmp-3 tmp-4 tmp-5 tmp-6 tmp-7 tmp-8 tmp-8-1 tmp-99 x-pnt-ins y-pnt-ins y-pnt-ins-1)

(setq cntr-1 0);setq

(setvar "textstyle" "Standard")

(repeat (length list-902)
	(setq tmp (nth cntr-1 list-902)
				tmp-1 (cdr (assoc 1 tmp))
				tmp-2 (cdr (assoc 2 tmp))
				tmp-3 (cdr (assoc 3 tmp))
				tmp-4 (cdr (assoc 4 tmp))
				tmp-5 (cdr (assoc 5 tmp))
				tmp-6 (cdr (assoc 6 tmp))
				tmp-99 (cdr (assoc 99 tmp))
	);setq
	
	(setvar "osmode" 6199)
	
	(setq pnt-ins		(getpoint "\nУкажите точку вставки\n")
	  		x-pnt-ins (nth 0 pnt-ins)
	 			y-pnt-ins (nth 1 pnt-ins)
	  		y-pnt-ins-1 y-pnt-ins
	  		dlt-y 8
	); setq
	
	(101-empt-lin-spcf)
	
	;///////////////////////////////////////////////////////////////////
	(if (= tmp-1 "ТТЖ-М исп. 1П")
		(progn
			(setq nmbr-ln 4);setq
			
			(1000-delete-items-spcf nmbr-ln x-pnt-ins y-pnt-ins)
			(1000-delete-items-spcf-crtf nmbr-ln x-pnt-ins y-pnt-ins)
			
			(command "_text" "_ML" (list (+ x-pnt-ins 1) (- (- y-pnt-ins (* dlt-y 0)) 4)) 2.5 0 "Термометр технический жидкостной (прямой)")
			(command "_text" "_ML" (list (+ x-pnt-ins 5) (- (- y-pnt-ins (* dlt-y 1)) 4)) 2.5 0 (strcat "- исп. 1, диапазон изм. " tmp-2 " %%dC, цена деления " tmp-4 " %%dC"))
			(command "_text" "_ML" (list (+ x-pnt-ins 5) (- (- y-pnt-ins (* dlt-y 2)) 4)) 2.5 0 (strcat "- длина верхней части " tmp-5 ", длина нижней части " tmp-6))
			;
			(command "_TEXT" "_MC" (list (+ x-pnt-ins 160) (- (- y-pnt-ins (* dlt-y 0)) 4)) 2.5 0 (strcat "ТТЖ-М исп. 1 №" tmp-3)) ;Тип, марка, обозначение документа, опросного листа
			(command "_text" "_MC" (list (+ x-pnt-ins 160) (- (- y-pnt-ins (* dlt-y 1)) 4)) 2.5 0 (strcat "(" tmp-2 "%%dC)-" tmp-4 "-" tmp-5 "/" tmp-6))
			;
;			(command "_text" "_ML" (list (+ x-pnt-ins 336) (- (- y-pnt-ins (* dlt-y 0)) 4)) 2.5 0 dt-8-01)
;			(command "_text" "_ML" (list (+ x-pnt-ins 336) (- (- y-pnt-ins (* dlt-y 1)) 4)) 2.5 0 (strcat "в Госреестре СИ"))
		
;			(command "_text" "_MC" (list (+ x-pnt-ins 247.5) (- (- y-pnt-ins (* dlt-y 0)) 4)) 2.5 0 "ПАО \"Стеклоприбор\",")
;			(command "_text" "_MC" (list (+ x-pnt-ins 247.5) (- (- y-pnt-ins (* dlt-y 1)) 4)) 2.5 0 "Украина, г. Червонозаводское")	
			
			(command "_text" "_MC" (list (+ x-pnt-ins 280) (- (- y-pnt-ins (* dlt-y 0)) 4)) 2.5 0 "шт.")
		);progn
	);if
	
				
	(command "_text" "_MC" (list (+ x-pnt-ins 322.5) (- (- y-pnt-ins (* dlt-y 0)) 4)) 2.5 0 tmp-99);масса
	
	(repeat nmbr-ln
  	(command "_insert" "зс-пустая-строка" "_X" 1 "_Y" 1 "_Z" 1 "_R" 0 (list x-pnt-ins y-pnt-ins-1))
  	(setq y-pnt-ins-1 (- y-pnt-ins-1 8));setq
	);repeat
 
	(setq cntr-1 (+ cntr-1 1));setq
);repeat

(princ)
)
;;;;////////////////////////////////////////////////////////////////////////////////////////////////////////////////////////////////////////////////////////////////////////////
;;;;////////////////////////////////////////////////////////////////////////////////////////////////////////////////////////////////////////////////////////////////////////////
