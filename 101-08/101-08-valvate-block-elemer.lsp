;/////// ************************************************************ ///////////////////////////////////////////////////////////////////////////////////////////////////////////
;/////// клапанные блоки "элемер"                                     ///////////////////////////////////////////////////////////////////////////////////////////////////////////
;/////// ************************************************************ ///////////////////////////////////////////////////////////////////////////////////////////////////////////
(defun 101-08-valvate-block-elemer

( / adoc dcl-id list-01 list-02 list-03 list-04 list-05 list-06 list-07 list-08 list-09 list-901 list-902 str-01 str-f type-list)

(vl-load-com)
(vla-startundomark (setq adoc (vla-get-activedocument (vlax-get-acad-object)))); start undo

(setvar "cmdecho" 0)
(setvar "textstyle" "Standard")

(setq str-f 1;переменные
			str-01 nil
      list-01 (list "Серия А"
      							"Серия Е"
      							"Серия С"
      							)
			list-02 nil
			list-03 nil
			list-04 nil
			list-05 nil
			list-06 nil
			list-07 nil
			list-08 nil
			list-09 nil

			list-901 nil	
			list-902 nil
);setq

(start-101-08-valvate-block-elemer)

(if (< (setq dcl-id (load_dialog "dia-101-08-valvate-block-elemer.dcl")) 0) ;ищем диалог
		(progn
			(alert "Не найден dcl-файл")
			(exit)
		);progn
);if

(if (not (new_dialog "dia_101_valvate_block_elemer" dcl-id))
		(exit)
);if

(list-filling "txt-01" list-01)
(list-filling "txt-02" list-02)
(list-filling "txt-03" list-03)
(list-filling "txt-04" list-04)
(list-filling "txt-05" list-05)
(list-filling "txt-06" list-06)
(list-filling "txt-07" list-07)
(list-filling "txt-08" list-08)
(list-filling "txt-09" list-09)

(set_tile "txt-01" "0")
(set_tile "txt-02" "0")
(set_tile "txt-03" "0")
(set_tile "txt-04" "0")
(set_tile "txt-05" "0")
(set_tile "txt-06" "0")
(set_tile "txt-07" "0")
(set_tile "txt-08" "0")
(set_tile "txt-09" "0")

(action_tile "txt-01"
  (strcat "(start-101-08-valvate-block-elemer)");srcat
);action_tile

(action_tile "txt-02"
  (strcat "(set_tile \"txt-03\" $value)");srcat
);action_tile

(action_tile "txt-03"
  (strcat "(set_tile \"txt-02\" $value)");srcat
);action_tile

(action_tile "txt-06"
  (strcat "(txt-06-101-08-valvate-block-elemer)");srcat
);action_tile

(action_tile "but1"
  (strcat "(but1-101-08-valvate-block-elemer)"
  );strcat
);action_tile

(action_tile "but2"
  (strcat "(setq type-list \"le\")"
          "(done_dialog)"
  );strcat
);action_tile

(action_tile "but3"
  (strcat "(setq type-list \"spcf\")"
          "(done_dialog)"
  );strcat
);action_tile

(action_tile "accept"
  (strcat "(done_dialog)"
          "(exit)"
  );strcat
);action_tile

(start_dialog)
(unload_dialog dcl-id)

(cond
	((= type-list "le") (le-101-08-valvate-block-elemer));=
	((= type-list "spcf") (spcf-101-08-valvate-block-elemer));=
);if

(setvar "osmode" 6199)
(setvar "cmdecho" 1)
(vla-endundomark adoc)
(princ)
)
;/////// ************************************************************ ///////////////////////////////////////////////////////////////////////////////////////////////////////////
;/////// конец программы                                             ////////////////////////////////////////////////////////////////////////////////////////////////////////////
;/////// ************************************************************ ///////////////////////////////////////////////////////////////////////////////////////////////////////////

;;;;/////////////////////////////////////////////////////////////////////////////////////////////////////////////////////////////////////////////////////////////////////////////
;;;;/////////////////////////////////////////////////////////////////////////////////////////////////////////////////////////////////////////////////////////////////////////////
(defun start-101-08-valvate-block-elemer

( / )

(if (= nil str-01) 
	(setq str-01 (nth 0 list-01));setq
	(setq str-01 (nth (atoi (get_tile "txt-01")) list-01));setq
);if

(if (= str-01 "Серия С")
	(progn
		(set_tile "ptxt-01" "Серия С - подключение импульсных линий напрямую к клапанному блоку через приварные штуцеры с наружной резьбой М20х1,5 или, по согласованию с заказчиком, через отверстия К1/2\" (1/2NPT), К1/4\" (1/4NPT) в теле блока")

		(setq list-02 (list "3" "3" "5" "5" "2")
					list-03 (list "30  Уплотнение шариком, без дренажа, без возможности подключ. метрологического оборудования" 
												"3И0  Уплотнение иглой, без дренажа, без возможности подключ. метрологического оборудования"
												"52  Уплотнение шариком, дренажный клапан после изолирующего вентиля, возможность подключ. метрологического оборудования" 
												"5И2  Уплотнение иглой, дренажный клапан после изолирующего вентиля, возможность подключ. метрологического оборудования"													
												"20  Уплотнение иглой, без дренажа, без возможности подключ. метрологического оборудования")
      		list-04 (list "02 AISI 316")     				
     			list-05 (list "Р5 наружная резьба М20х1,5 под плоский ниппель")
     			list-06 (list "- Общепромышленное" "К Кислородное")
      		list-07 (list "- Нет"
												"ДР* болты, шайбы, резиновые уплотнительные кольца" 
												"ДФ болты, шайбы, фторопластовые уплотнительные кольца" 
												"СР болты 7/16UNF, шайбы, резиновые уплотнительные кольца"
												"СФ болты 7/16UNF, шайбы, фторопластовые уплотнительные кольца")
      		list-08 (list "- Нет"
      									"М20Ф ниппели сталь 12Х18Н10Т, накидные гайки М20х1,5 для соединения по наружному диаметру трубы 14 мм, прокладки из фторопласта"
      									"М20М ниппели сталь 12Х18Н10Т, накидные гайки М20х1,5 для соединения по наружному диаметру трубы 14 мм, прокладки из меди"
      									"М20УФ ниппели углеродистая сталь, накидные гайки М20х1,5 для соединения по наружному диаметру трубы 14 мм, прокладки из фторопласта"
      									"М20УМ ниппели углеродистая сталь, накидные гайки М20х1,5 для соединения по наружному диаметру трубы 14 мм, прокладки из меди")
      		list-09 (list "- Нет" 
      									"Т Скоба, кронштейн для крепления клапанного блока на трубе Ду50 мм, труба - горизонтально"
      									"КР3 Скоба, кронштейн для крепления датчика на трубе Ду50 мм, труба - горизонтально"
      									"КР3С Скоба, кронштейн для крепления датчика на трубе Ду50 мм, труба - горизонтально"
      									"СК Скоба, кронштейн для крепления датчика на трубе Ду50 мм, труба - вертикально"
      									"СКС Скоба, кронштейн для крепления датчика на трубе Ду50 мм, труба - вертикально")      			
		);setq
	);progn
);=


;(if (= str-01 "Серия А")
;	(progn
;		(set_tile "ptxt-01" "Серия А - Присоединение импульсных линий к клапанному блоку через монтажные фланцы")
;
;		(setq list-02 (list "3" "3" "5" "5" "2")
;					list-03 (list "30  Уплотнение шариком, без дренажа, без возможности подключ. метрологического оборудования" 
;												"И0  Уплотнение иглой, без дренажа, без возможности подключ. метрологического оборудования"
;												"52  Уплотнение шариком, дренажный клапан после изолирующего вентиля, возможность подключ. метрологического оборудования" 
;												"5И2  Уплотнение иглой, дренажный клапан после изолирующего вентиля, возможность подключ. метрологического оборудования"													
;												"20  Уплотнение иглой, без дренажа, без возможности подключ. метрологического оборудования")
;      		list-04 (list "02 AISI 316")     				
;     			list-05 (list "Р5 наружная резьба М20х1,5 под плоский ниппель")
;     			list-06 (list "- Общепромышленное" "К Кислородное")
;      		list-07 (list "- Нет"
;												"ДР* болты, шайбы, резиновые уплотнительные кольца" 
;												"ДФ болты, шайбы, фторопластовые уплотнительные кольца" 
;												"СР болты 7/16UNF, шайбы, резиновые уплотнительные кольца"
;												"СФ болты 7/16UNF, шайбы, фторопластовые уплотнительные кольца")
;      		list-08 (list "- Нет"
;      									"М20Ф ниппеля сталь 12Х18Н10Т, накидные гайки М20х1,5 для соединения по наружному диаметру трубы 14 мм, прокладки из фторопласта"
;      									"М20М ниппеля сталь 12Х18Н10Т, накидные гайки М20х1,5 для соединения по наружному диаметру трубы 14 мм, прокладки из меди"
;      									"М20УФ ниппеля углеродистая сталь, накидные гайки М20х1,5 для соединения по наружному диаметру трубы 14 мм, прокладки из фторопласта"
;      									"М20УМ ниппеля углеродистая сталь, накидные гайки М20х1,5 для соединения по наружному диаметру трубы 14 мм, прокладки из меди")
;      		list-09 (list "- Нет" 
;      									"Т Скоба, кронштейн для крепления клапанного блока на трубе Ду50 мм, труба - горизонтально"
;      									"КР3 Скоба, кронштейн для крепления датчика на трубе Ду50 мм, труба - горизонтально"
;      									"КР3С Скоба, кронштейн для крепления датчика на трубе Ду50 мм, труба - горизонтально"
;      									"СК Скоба, кронштейн для крепления датчика на трубе Ду50 мм, труба - вертикально"
;      									"СКС Скоба, кронштейн для крепления датчика на трубе Ду50 мм, труба - вертикально")      			
;		);setq
;	);progn
;);=


(list-filling "txt-02" list-02)
(list-filling "txt-03" list-03)
(list-filling "txt-04" list-04)
(list-filling "txt-05" list-05)
(list-filling "txt-06" list-06)
(list-filling "txt-07" list-07)
(list-filling "txt-08" list-08)
(list-filling "txt-09" list-09)
(list-filling "txt-10" list-10)
(list-filling "txt-11" list-11)
(list-filling "txt-12" list-12)
(list-filling "txt-13" list-13)

(set_tile "txt-02" "0")
(set_tile "txt-03" "0")
(set_tile "txt-04" "0")
(set_tile "txt-05" "0")
(set_tile "txt-06" "0")
(set_tile "txt-07" "0")
(set_tile "txt-08" "0")
(set_tile "txt-09" "0")
(set_tile "txt-10" "0")
(set_tile "txt-11" "0")
(set_tile "txt-12" "0")
(set_tile "txt-13" "0")

(princ)
)
;;;;/////////////////////////////////////////////////////////////////////////////////////////////////////////////////////////////////////////////////////////////////////////////
;;;;/////////////////////////////////////////////////////////////////////////////////////////////////////////////////////////////////////////////////////////////////////////////

;/////// ************************************************************ ///////////////////////////////////////////////////////////////////////////////////////////////////////////
;///////                                                              ///////////////////////////////////////////////////////////////////////////////////////////////////////////
(defun txt-06-101-08-valvate-block-elemer

( / str-01 str-02)

(setq str-01 (nth (atoi (get_tile "txt-01")) list-01)
			str-06 (nth (atoi (get_tile "txt-06")) list-06)
);setq

(if (= str-01 "Серия С")
	(cond
		((= str-06 "- Общепромышленное")
			(setq list-02 (list "3" "3" "5" "5" "2")
						list-03 (list "30  Уплотнение шариком, без дренажа, без возможности подключ. метрологического оборудования" 
													"3И0  Уплотнение иглой, без дренажа, без возможности подключ. метрологического оборудования"
													"52  Уплотнение шариком, дренажный клапан после изолирующего вентиля, возможность подключ. метрологического оборудования" 
													"5И2  Уплотнение иглой, дренажный клапан после изолирующего вентиля, возможность подключ. метрологического оборудования"													
													"20  Уплотнение иглой, без дренажа, без возможности подключ. метрологического оборудования")
			);setq
		);=

		((= str-06 "К Кислородное")
			(setq list-02 (list "3" "5" "2")
						list-03 (list "3И0  Уплотнение иглой, без дренажа, без возможности подключ. метрологического оборудования"													
													"5И2  Уплотнение иглой, дренажный клапан после изолирующего вентиля, возможность подключ. метрологического оборудования"													
													"20  Уплотнение иглой, без дренажа, без возможности подключ. метрологического оборудования")
			);setq
		);=
	);cond
);if

(list-filling "txt-02" list-02)
(list-filling "txt-03" list-03)

(set_tile "txt-02" "0")
(set_tile "txt-03" "0")

(princ)
)
;;;;/////////////////////////////////////////////////////////////////////////////////////////////////////////////////////////////////////////////////////////////////////////////
;;;;/////////////////////////////////////////////////////////////////////////////////////////////////////////////////////////////////////////////////////////////////////////////



;/////// ************************************************************ ///////////////////////////////////////////////////////////////////////////////////////////////////////////
;/////// формирование данных, заполнение поля "выбрано"               ///////////////////////////////////////////////////////////////////////////////////////////////////////////
(defun but1-101-08-valvate-block-elemer

( / str-01 str-02 str-03 str-04 str-05 str-06 str-07 str-08 str-09 str-902 swtch)

(setq str-01 (nth (atoi (get_tile "txt-01")) list-01)
			str-02 (nth (atoi (get_tile "txt-02")) list-02)
			str-03 (nth (atoi (get_tile "txt-03")) list-03)
			str-04 (nth (atoi (get_tile "txt-04")) list-04)
			
			str-06 (nth (atoi (get_tile "txt-06")) list-06)
			str-07 (nth (atoi (get_tile "txt-07")) list-07)
			str-08 (nth (atoi (get_tile "txt-08")) list-08)
			str-09 (nth (atoi (get_tile "txt-09")) list-09)
      swtch list-901
);setq

(if (/= swtch nil) (setq list-902 (reverse list-902)));if

(if (= str-01 "Серия С")
	(progn
		(setq str-05 (nth (atoi (get_tile "txt-05")) list-05))
		(setq list-901 (vl-list* (strcat str-01 "  " 
																		 "Кол. вентилей " str-02 "  " 
																		 "Схема " (substr str-03 1 (vl-string-search " " str-03)) "  "
																		 "Материал " (substr str-04 1 (vl-string-search " " str-04)) "  "
																		 (substr str-05 1 (vl-string-search " " str-05)) "  " 
																		 "Исполнение " (substr str-06 1 (vl-string-search " " str-06)) "  "
																		 "МК " (substr str-07 1 (vl-string-search " " str-07)) "  " 
																		 "КМЧ " (substr str-08 1 (vl-string-search " " str-08)) "  "
																		 "Кронштейн " (substr str-09 1 (vl-string-search " " str-09))
																		  ) list-901)  
																		  
		);setq

		(setq str-902 (list (cons 1 str-01) (cons 2 str-02) (cons 3 str-03) (cons 4 str-04) (cons 5 str-05) (cons 6 str-06) (cons 7 str-07)	(cons 8 str-08) (cons 9 str-09) (cons 99 "1,5"))
					list-902 (vl-list* str-902 list-902)
		);setq
	);progn	
);if

(setq list-902 (reverse list-902));setq

(list-filling "txt-901" (reverse list-901))

(princ)
)
;;;;/////////////////////////////////////////////////////////////////////////////////////////////////////////////////////////////////////////////////////////////////////////////
;;;;/////////////////////////////////////////////////////////////////////////////////////////////////////////////////////////////////////////////////////////////////////////////

;/////// ************************************************************ ///////////////////////////////////////////////////////////////////////////////////////////////////////////
;/////// вывод в ПЭ                                                   ///////////////////////////////////////////////////////////////////////////////////////////////////////////
(defun le-101-08-valvate-block-elemer

( / cntr-1 dlt-y nmbr-ln pnt-ins str-01 str-03 str-03-1 str-03-2 str-03-3 str-06 str-tmp x-pnt-ins y-pnt-ins y-pnt-ins-1)

(setq cntr-1 0);setq

(setvar "textstyle" "Standard")

(repeat (length list-902)
	(setq str-tmp (nth cntr-1 list-902)
				str-01 (cdr (assoc 1 str-tmp))				
				str-03 (cdr (assoc 3 str-tmp))
				str-06 (cdr (assoc 6 str-tmp))
	);setq

;(princ "\n         str-tmp = ") (princ str-tmp);Erase_DV
;(getstring "\nPress Enter to continue...");Erase_DV


	(setvar "osmode" 6199)
	(setq pnt-ins		(getpoint "\nУкажите точку вставки\n")
  			x-pnt-ins (nth 0 pnt-ins)
 				y-pnt-ins (nth 1 pnt-ins)
  			y-pnt-ins-1 y-pnt-ins
  			dlt-y 8
	); etq
	
	(100-empt-lin-le)
	(setvar "osmode" 0)
	(setvar "cmdecho" 0)
	
	;/////////////////////////////////////////////////////////////////////////////////////////////////
	(if (= str-01 "Серия С")
		(progn 
			(setq str-03 (substr str-03 1 (vl-string-search " " str-03))
						str-03-1 (substr str-03 1 1)
						str-06 (substr str-06 (vl-string-search " " str-06))
						str-06 (strcase (substr str-06 (+ (vl-string-search " " str-06) 2)) 1)
			);setq
		
			(cond
				((= str-03 "30") (setq str-03-2 "уплотнение шариком" str-03-3 "без дренажа" ));=
				((= str-03 "3И0") (setq str-03-2 "уплотнение иглой" str-03-3 "без дренажа" ));=
				((= str-03 "52") (setq str-03-2 "уплотнение шариком" str-03-3 "с дренажом" ));=
				((= str-03 "5И2") (setq str-03-2 "уплотнение иглой" str-03-3 "с дренажом" ));=
				((= str-03 "20") (setq str-03-2 "уплотнение иглой" str-03-3 "без дренажа" ));=
			);cond

			(setq nmbr-ln 4);setq
			(1000-delete-items-le nmbr-ln x-pnt-ins y-pnt-ins)
			(setvar "osmode" 0)
			(setvar "cmdecho" 0)
			
			(command "_text" "_ML" (list (+ x-pnt-ins 1) (- (- y-pnt-ins (* dlt-y 0)) 4)) 2.5 0 (strcat "Клапанный блок Элемер-БК-С" str-03 " (приварные штуцеры),"))
			(command "_text" "_ML" (list (+ x-pnt-ins 1) (- (- y-pnt-ins (* dlt-y 1)) 4)) 2.5 0 (strcat "количество вентилей " str-03-1 ", " str-03-3 ", " str-03-2 ","))
			(command "_text" "_ML" (list (+ x-pnt-ins 1) (- (- y-pnt-ins (* dlt-y 2)) 4)) 2.5 0 (strcat "исполнение " str-06))
		);progn
	);if


	
	(setq cntr-1 (1+ cntr-1));setq
	
	(repeat nmbr-ln
  	(command "_insert" "пэ-пустая-строка" "_X" 1 "_Y" 1 "_Z" 1 "_R" 0 (list x-pnt-ins y-pnt-ins-1))
  	(setq y-pnt-ins-1 (- y-pnt-ins-1 8));setq
	);repeat
	(setvar "osmode" 6199)
);repeat

(princ)
)
;;;;/////////////////////////////////////////////////////////////////////////////////////////////////////////////////////////////////////////////////////////////////////////////
;;;;/////////////////////////////////////////////////////////////////////////////////////////////////////////////////////////////////////////////////////////////////////////////

;/////// ************************************************************ ///////////////////////////////////////////////////////////////////////////////////////////////////////////
;/////// вывод в СПЦФ базовая                                         ///////////////////////////////////////////////////////////////////////////////////////////////////////////
(defun spcf-101-08-valvate-block-elemer

( / cntr-1 dlt-y nmbr-ln pnt-ins str-01 str-02 str-03 str-03-1 str-03-2 str-06 str-06-1 str-06-2 str-07 str-07-1 str-07-2 str-08 str-08-1 str-08-2 str-09 str-09-1 str-09-2 
str-99 str-tmp x-pnt-ins y-pnt-ins y-pnt-ins-1)

(setq cntr-1 0);setq

(setvar "textstyle" "Standard")

(repeat (length list-902)
	(setq str-tmp (nth cntr-1 list-902)
				str-01 (cdr (assoc 1 str-tmp))
				str-99 (cdr (assoc 99 str-tmp));масса
	);setq
	
;(princ "\n         str-tmp = ") (princ str-tmp);Erase_DV
;(getstring "\nPress Enter to continue...");Erase_DV
	
	(setvar "osmode" 6199)
	(setq pnt-ins		(getpoint "\nУкажите точку вставки\n")
				x-pnt-ins (nth 0 pnt-ins)
				y-pnt-ins (nth 1 pnt-ins)
				y-pnt-ins-1 y-pnt-ins
				dlt-y 8
	); setq

	(101-empt-lin-spcf)
	(setvar "osmode" 0)
	(setvar "cmdecho" 0)	
	
	
	(if (= str-01 "Серия С")
		(progn
			(setq str-02 (cdr (assoc 2 str-tmp))
						str-03 (cdr (assoc 3 str-tmp))
						str-06 (cdr (assoc 6 str-tmp))
						str-07 (cdr (assoc 7 str-tmp))
						str-08 (cdr (assoc 8 str-tmp))
						str-09 (cdr (assoc 9 str-tmp))
			);setq
				
			(setq str-03-1 (substr str-03 1 (vl-string-search " " str-03))
						
						str-06-1 (substr str-06 1 (vl-string-search " " str-06))						
						str-06 (substr str-06 (vl-string-search " " str-06))
						str-06-2 (strcase (substr str-06 (+ (vl-string-search " " str-06) 2)) 1)
				
						str-07-1 (substr str-07 1 (vl-string-search " " str-07))
						str-07-1 (vl-string-right-trim "*" str-07-1)
				
						str-08-1 (substr str-08 1 (vl-string-search " " str-08))
				
						str-09-1 (substr str-09 1 (vl-string-search " " str-09))		
			);setq
		
			(cond
				((= str-03-1 "30") (setq str-03-2 "уплотнение шариком, без дренажа"));=
				((= str-03-1 "3И0") (setq str-03-2 "уплотнение иглой, без дренажа"));=
				((= str-03-1 "52") (setq str-03-2 "уплотнение шариком, с дренажом"));=
				((= str-03-1 "5И2") (setq str-03-2 "уплотнение иглой, с дренажом"));=
				((= str-03-1 "20") (setq str-03-2 "уплотнение иглой, без дренажа"));=
			);cond

			(cond
				((= str-07 "- Нет") (setq str-07-2 (strcat "без монтажного комплекта для крепления к датчику, код " str-07-1)));=
				((/= str-07 "- Нет") (setq str-07-2 (strcat "монтажный комплект для крепления к датчику, код " str-07-1)));=
			);cond

			(cond
				((= str-08 "- Нет") (setq str-08-2 (strcat "без комплекта монтажных частей для присоединения к процессу, код " str-08-1)));=
				((/= str-08 "- Нет") (setq str-08-2 (strcat "комплект монтажных частей для присоединения к процессу, код " str-08-1)));=
			);cond

			(cond
				((= str-09 "- Нет") (setq str-09-2 (strcat "без скобы и кронштейна для крепления на трубе Ду50 мм, код " str-09-1)));=
				((/= str-09 "- Нет") (setq str-09-2 (strcat "скоба и кронштейн для крепления на трубе Ду50 мм, код " str-09-1)));=
			);cond

			(setq nmbr-ln 9);setq
			
			(1000-delete-items-spcf nmbr-ln x-pnt-ins y-pnt-ins);удаление предыдущей записи
			(1000-delete-items-spcf-crtf nmbr-ln x-pnt-ins y-pnt-ins);удаление предыдущего сертификата
		
			(command "_text" "_ML" (list (+ x-pnt-ins 1) (- (- y-pnt-ins (* dlt-y 0)) 4)) 2.5 0 (strcat "Клапанный блок"))
			(command "_text" "_ML" (list (+ x-pnt-ins 5) (- (- y-pnt-ins (* dlt-y 1)) 4)) 2.5 0 "- серия С (присоединение импульсных линий через приварные штуцеры)")
			(command "_text" "_ML" (list (+ x-pnt-ins 5) (- (- y-pnt-ins (* dlt-y 2)) 4)) 2.5 0 (strcat "- количество вентилей " str-02 ", " str-03-2))
			(command "_text" "_ML" (list (+ x-pnt-ins 5) (- (- y-pnt-ins (* dlt-y 3)) 4)) 2.5 0 "- соединение на входе среды наружная резьба М20х1,5, код Р5")
			(command "_text" "_ML" (list (+ x-pnt-ins 5) (- (- y-pnt-ins (* dlt-y 4)) 4)) 2.5 0 (strcat "- исполнение " str-06-2))
			(command "_text" "_ML" (list (+ x-pnt-ins 5) (- (- y-pnt-ins (* dlt-y 5)) 4)) 2.5 0 (strcat "- " str-07-2))
			(command "_text" "_ML" (list (+ x-pnt-ins 5) (- (- y-pnt-ins (* dlt-y 6)) 4)) 2.5 0 (strcat "- " str-08-2))
			(command "_text" "_ML" (list (+ x-pnt-ins 5) (- (- y-pnt-ins (* dlt-y 7)) 4)) 2.5 0 (strcat "- " str-09-2))
			 
	
			(command "_TEXT" "_MC" (list (+ x-pnt-ins 160) (- (- y-pnt-ins (* dlt-y 0)) 4)) 2.5 0 (strcat "Элемер-БК-С" str-03-1 " / 02 / Р5 / " str-06-1 " / "));Тип, марка, обозначение документа, опросного листа
			(command "_TEXT" "_MC" (list (+ x-pnt-ins 160) (- (- y-pnt-ins (* dlt-y 1)) 4)) 2.5 0 (strcat str-07-1 " / " str-08-1 " / " str-09-1 " / "))
			(command "_TEXT" "_MC" (list (+ x-pnt-ins 160) (- (- y-pnt-ins (* dlt-y 2)) 4)) 2.5 0 "ТУ 3742-084-13282997-08")

		);progn
	);if

	(command "_text" "_MC" (list (+ x-pnt-ins 247.5) (- (- y-pnt-ins (* dlt-y 0)) 4)) 2.5 0 "ООО НПП \"ЭЛЕМЕР\",")
	(command "_text" "_MC" (list (+ x-pnt-ins 247.5) (- (- y-pnt-ins (* dlt-y 1)) 4)) 2.5 0 "г. Москва, Зеленоград")
	
	(command "_text" "_MC" (list (+ x-pnt-ins 280) (- (- y-pnt-ins (* dlt-y 0)) 4)) 2.5 0 "шт.")

	(command "_text" "_MC" (list (+ x-pnt-ins 322.5) (- (- y-pnt-ins (* dlt-y 0)) 4)) 2.5 0 str-99);масса
 
	(repeat nmbr-ln
  	(command "_insert" "зс-пустая-строка" "_X" 1 "_Y" 1 "_Z" 1 "_R" 0 (list x-pnt-ins y-pnt-ins-1))
  	(setq y-pnt-ins-1 (- y-pnt-ins-1 8));setq
	);repeat

	(setq cntr-1 (+ cntr-1 1));setq
);repeat

(princ)
)
;;;;/////////////////////////////////////////////////////////////////////////////////////////////////////////////////////////////////////////////////////////////////////////////
;;;;/////////////////////////////////////////////////////////////////////////////////////////////////////////////////////////////////////////////////////////////////////////////
