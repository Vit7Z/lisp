;/////// ************************************************************ //////////////////////////////////////////////////////////////////
;/////// обозначение диаметра трубы                                   //////////////////////////////////////////////////////////////////
;/////// ************************************************************ //////////////////////////////////////////////////////////////////
(defun c:700-diameter-of-a-pipe

( / adoc)

(vl-load-com)
(vla-startundomark
  (setq adoc (vla-get-activedocument (vlax-get-acad-object))
  );setq
) ; start undo
(setvar "cmdecho" 0)

(command "_.qleader" "_s")



(setvar "osmode" 6199)
(setvar "cmdecho" 1)
(vla-endundomark adoc)
(princ)
)
;/////// конец программы ///////
