;/////// *************************************************************///////////////////////////////////////////////////////////////////////////////////////////////////////////
;/////// задвижка                                                     ///////////////////////////////////////////////////////////////////////////////////////////////////////////
;/////// *************************************************************///////////////////////////////////////////////////////////////////////////////////////////////////////////
(defun c:699-gost-21-205-gate-valve

( / adoc angl-blck lin-1 lin-2 lin-3 lin-4 lin-5 pnt-drctn pnt-ins)

(vl-load-com)
(vla-startundomark
  (setq adoc (vla-get-activedocument (vlax-get-acad-object)));setq
);undo

(setvar "cmdecho" 0)

(if	(= (tblsearch "block" "задвижка-гост-21-205-схтх") nil);создаем блок
  (progn
    (setvar "osmode" 0)
    (command "_line" '(-3 1.5) '(3 -1.5) "")
    (setq lin-1 (entlast))
    (command "_line" '(-3 -1.5) '(3 1.5) "")
    (setq lin-2 (entlast))
    (command "_line" '(-3 1.5) '(-3 -1.5) "")
    (setq lin-3 (entlast))
    (command "_line" '(3 1.5) '(3 -1.5) "")
    (setq lin-4 (entlast))  
    (command "_line" '(0 1.5) '(0 -1.5) "")
    (setq lin-5 (entlast))         
		(command "_block" "задвижка-гост-21-205-схтх" '(-3 0) lin-1 lin-2 lin-3 lin-4 lin-5 "");command
  );progn
);if

(setvar "osmode" 6199)
(setvar "orthomode" 1)

(while (/= (setq pnt-ins (getpoint "\nУкажите точку вставки\n")) nil)
  (setq pnt-drctn	 (getpoint "\nУкажите точку направления\n")
			  angl-blck (angtos (angle pnt-ins pnt-drctn) 1)
  );setq
  
  (setvar "osmode" 0)
  
  (command "_insert" "задвижка-гост-21-205-схтх" "_X" 1 "_Y" 1 "_Z" 1 "_R" angl-blck pnt-ins)
  
  (setvar "osmode" 6199)
);while

(setvar "osmode" 6199)
(setvar "cmdecho" 1)
(vla-endundomark adoc)
(princ)
)
;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////
