;/////// ************************************************************ //////////////////////////////////////////////////////////////////////////////////////////////////////////
;/////// Клапан (вентиль) обратный проходной ГОСТ 21.205-93, ГОСТ 2.784-96 /////////////////////////////////////////////////////////////////////////////////////////////////////
;/////// ************************************************************ //////////////////////////////////////////////////////////////////////////////////////////////////////////
(defun c:699-gost-21-205-valve-return-checkpoint

( / adoc angl-blck hatch-1 lin-1 lin-2 lin-3 lin-4 lin-5 lin-6 pnt-drctn pnt-ins)

(vl-load-com)
(vla-startundomark
  (setq adoc (vla-get-activedocument (vlax-get-acad-object))
  );setq
) ; start undo
(setvar "cmdecho" 0)
(setvar "auprec" 7)

(if	(= (tblsearch "block" "клапан-обратный-проходной-гост-21-205-схтх") nil);создаем блок
  (progn
    (setvar "osmode" 0)
    (command "_line" '(0 1.5) '(0 -1.5) "")
    (setq lin-1 (entlast))
    
    (command "_line" '(0 1.5) '(3 0) "")
    (setq lin-2 (entlast))
    
    (command "_line" '(0 -1.5) '(3 0) "")
    (setq lin-3 (entlast))
        
    (command "_line" '(3 0) '(6 1.5) "")
    (setq lin-4 (entlast))    
     
    (command "_line" '(3 0) '(6 -1.5) "")
    (setq lin-5 (entlast)) 
     
    (command "_line" '(6 1.5) '(6 -1.5) "")
    (setq lin-6 (entlast)) 

    (command "_hatch" "solid" lin-4 lin-5 lin-6 "")
		(setq hatch-1 (entlast))

		(command "_block" "клапан-обратный-проходной-гост-21-205-схтх" '(0 0) lin-1 lin-2 lin-3 lin-4  lin-5 lin-6 hatch-1 "");command
  ) ; конец progn
);if	

(setvar "osmode" 6199)
(while (/= (setq pnt-ins (getpoint "\nУкажите точку вставки\n")) nil)
  (setq pnt-drctn	 (getpoint "\nУкажите точку направления\n")
	  		angl-blck (angtos (angle pnt-ins pnt-drctn) 1)
  );setq

  (setvar "osmode" 0)
  (command "_insert" "клапан-обратный-проходной-гост-21-205-схтх" "_X" 1 "_Y" 1 "_Z" 1 "_R" angl-blck pnt-ins)
  (setvar "osmode" 6199)
);while

(setvar "cmdecho" 1)
(vla-endundomark adoc)
(princ)
)

;/////// *************************************************************///////////////////////////////////////////////////////////////////////////////////////////////////////////
;/////// КОНЕЦ ПРОГРАММЫ                                              ///////////////////////////////////////////////////////////////////////////////////////////////////////////
;/////// *************************************************************///////////////////////////////////////////////////////////////////////////////////////////////////////////
