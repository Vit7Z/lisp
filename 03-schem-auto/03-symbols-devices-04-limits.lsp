;/////// ************************************************************ ///////////////////////////////////////////////////////////////////////////////////////////////////////////
;/////// прибор, переключение по "Н"                                  ///////////////////////////////////////////////////////////////////////////////////////////////////////////
;/////// ************************************************************ ///////////////////////////////////////////////////////////////////////////////////////////////////////////
(defun c:03-symbols-devices-04-limits

( / adoc dcl-id str-01 str-02 str-03 str-04)

(vl-load-com)
(vla-startundomark (setq adoc (vla-get-activedocument (vlax-get-acad-object))));start undo

(setq str-01 0
			str-02 0
			str-03 0
			str-04 0)

(if (< (setq dcl-id (load_dialog "dia-03-symbols-devices-04-limits.dcl")) 0) ;ищем диалог
	(progn
		(alert "Не найден dcl-файл")
		(exit)
	);progn
);if

(if (not (new_dialog "dia_03_symbols_devices_04_limits" dcl-id))
	(exit)
);if

(action_tile "tgl-01"
  (strcat "(setq str-01 1)");strcat
);action_tile

(action_tile "tgl-02"
  (strcat "(setq str-02 1)");strcat
);action_tile

(action_tile "tgl-03"
  (strcat "(setq str-03 1)");strcat
);action_tile

(action_tile "tgl-04"
  (strcat "(setq str-04 1)");strcat
);action_tile

(action_tile "accept"
  (strcat "(done_dialog)"
;          "(exit)"
  );strcat
);action_tile

(start_dialog)
(unload_dialog dcl-id)

(03-symbols-devices-04-limits-draw str-01 str-02 str-03 str-04)

(setvar "cmdecho" 0)
(setvar "osmode" 6199)

(vla-endundomark adoc)
(princ)
)
;/////// ************************************************************ ///////////////////////////////////////////////////////////////////////////////////////////////////////////
;/////// конец                                                        ///////////////////////////////////////////////////////////////////////////////////////////////////////////
;/////// ************************************************************ ///////////////////////////////////////////////////////////////////////////////////////////////////////////


;/////// ************************************************************ ///////////////////////////////////////////////////////////////////////////////////////////////////////////
;/////// прибор, переключение по "Н"                                  ///////////////////////////////////////////////////////////////////////////////////////////////////////////
;/////// ************************************************************ ///////////////////////////////////////////////////////////////////////////////////////////////////////////
(defun 03-symbols-devices-04-limits-draw

(str-01 str-02 str-03 str-04 / pnt-1 pnt-ins st-1 st-2 st-3 st-4 x-pnt-ins y-pnt-ins)

(while (/= (setq pnt-ins (getpoint "\nУкажите точку вставки\n")) nil)

	(setq	x-pnt-ins (nth 0 pnt-ins)				
	 			y-pnt-ins (nth 1 pnt-ins)
	 			
	 			st-1 (ssget "_c" (list (+ x-pnt-ins 3) (+ y-pnt-ins 3)) (list x-pnt-ins (+ y-pnt-ins 1)) '((0 . "*TEXT"))) ;рамка выбора H
	 			st-2 (ssget "_c" (list (+ x-pnt-ins 3) (- y-pnt-ins 3)) (list x-pnt-ins (- y-pnt-ins 1)) '((0 . "*TEXT"))) ;рамка выбора L
	 			st-3 (ssget "_c" (list (+ x-pnt-ins 3) (+ y-pnt-ins 6)) (list x-pnt-ins (+ y-pnt-ins 4.5)) '((0 . "*TEXT"))) ;рамка выбора HH
	 			st-4 (ssget "_c" (list (+ x-pnt-ins 3) (- y-pnt-ins 6)) (list x-pnt-ins (- y-pnt-ins 4.5)) '((0 . "*TEXT")))
	);setq

	(setvar "osmode" 0)
	
	;;;;;;;/////////////////////////////////////////////////////////////////////////////////////////////////////////////
	(if (= str-01 1) ;рисум предел H
		(progn
			(setq pnt-1 (polar pnt-ins (angtof "90" 0) 3))	;точка вставки текста
				
			(if (/= st-1 nil) (command "_erase" st-1 ""));if
				
			(command "_text" "_ml" pnt-1 2.5 0 "H")
		);progn

		(command "_erase" st-1 "")
	);if

  ;;;;;;;/////////////////////////////////////////////////////////////////////////////////////////////////////////////
	(if (= str-03 1) ;рисум предел L
		(progn
			(setq pnt-1 (polar pnt-ins (angtof "-90" 0) 3))	;точка вставки текста
	
			(if (/= st-2 nil) (command "_erase" st-2 ""));if
				
			(command "_text" "_ml" pnt-1 2.5 0 "L")
		);progn
		
		(command "_erase" st-2 "")
	);if
  
  ;;;;;;;/////////////////////////////////////////////////////////////////////////////////////////////////////////////
	(if (= str-02 1) ;рисум предел HH
		(progn
			(setq pnt-1 (polar pnt-ins (angtof "90" 0) 6))	;точка вставки текста
	
			(if (/= st-3 nil) (command "_erase" st-3 ""));if
				
			(command "_text" "_ml" pnt-1 2.5 0 "HH")
		);progn
		
		(command "_erase" st-3 "")
	);if

  ;;;;;;;/////////////////////////////////////////////////////////////////////////////////////////////////////////////
	(if (= str-04 1) ;рисум предел LL
		(progn
			(setq pnt-1 (polar pnt-ins (angtof "-90" 0) 6))	;точка вставки текста
	
			(if (/= st-4 nil) (command "_erase" st-4 ""));if
				
			(command "_text" "_ml" pnt-1 2.5 0 "LL")
		);progn
		
		(command "_erase" st-4 "")
	);if

	(setvar "osmode" 6199)
);while

(setvar "cmdecho" 1)

)
;/////// ************************************************************ ///////////////////////////////////////////////////////////////////////////////////////////////////////////
;/////// конец                                                        ///////////////////////////////////////////////////////////////////////////////////////////////////////////
;/////// ************************************************************ ///////////////////////////////////////////////////////////////////////////////////////////////////////////
