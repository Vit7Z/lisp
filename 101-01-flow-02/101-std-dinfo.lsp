;/////// ************************************************************ //////////////////////////////////////////////////////////////////
;/////// стд                                                          //////////////////////////////////////////////////////////////////
;/////// ************************************************************ //////////////////////////////////////////////////////////////////
(defun 101-std-dinfo

( / adoc file-open path-file-open pnt-ins standard-size str-diam str-f str-left str-mass str-size-1 str-size-2 x-pnt-ins y-pnt-ins)

(vl-load-com)
(vla-startundomark
  (setq adoc (vla-get-activedocument (vlax-get-acad-object))
  );setq
) ; start undo

(setvar "cmdecho" 0)
(setvar "textstyle" "Standard")

(setvar "osmode" 6199)
(setq pnt-ins		(getpoint "\nУкажите точку вставки\n")
	  x-pnt-ins (nth 0 pnt-ins)
	  y-pnt-ins (nth 1 pnt-ins)
	  y-pnt-ins-1 y-pnt-ins
); setq

(101-empt-lin-spcf)

(setvar "osmode" 0)
(setvar "cmdecho" 0)

(repeat 8
  (command "_insert" "зс-пустая-строка" "_X" 1 "_Y" 1 "_Z" 1 "_R" 0 (list x-pnt-ins y-pnt-ins-1))
  (setq y-pnt-ins-1 (- y-pnt-ins-1 8)
  );setq
);repeat

(command "_TEXT" "_ML" (list (+ x-pnt-ins 1) (- y-pnt-ins 4)) 2.5 0 "Счетчик в составе:");наименование
(command "_TEXT" "_ML" (list (+ x-pnt-ins 1) (- y-pnt-ins 44)) 2.5 0 "- Вычислитель")
(command "_TEXT" "_ML" (list (+ x-pnt-ins 5) (- y-pnt-ins 52)) 2.5 0 "- интерфейсы RS-232 и RS-485")

(command "_TEXT" "_MC" (list (+ x-pnt-ins 160) (- y-pnt-ins 4)) 2.5 0 "СТД-****,")
(command "_TEXT" "_MC" (list (+ x-pnt-ins 160) (- y-pnt-ins 12)) 2.5 0 "ТУ 4218-011-40637960-09,")
(command "_TEXT" "_MC" (list (+ x-pnt-ins 160) (- y-pnt-ins 20)) 2.5 0 "состав каналов")
(command "_TEXT" "_MC" (list (+ x-pnt-ins 160) (- y-pnt-ins 28)) 2.5 0 "(f: ** , имп.: ** , I: ** , R: **)")

(command "_TEXT" "_MC" (list (+ x-pnt-ins 160) (- y-pnt-ins 44)) 2.5 0 " ВТД-**")

(command "_TEXT" "_MC" (list (+ x-pnt-ins 280) (- y-pnt-ins 4)) 2.5 0 "шт.");количество
(command "_TEXT" "_MC" (list (+ x-pnt-ins 300) (- y-pnt-ins 4)) 2.5 0 "1")
(command "_TEXT" "_MC" (list (+ x-pnt-ins 280) (- y-pnt-ins 44)) 2.5 0 "шт.");количество
(command "_TEXT" "_MC" (list (+ x-pnt-ins 300) (- y-pnt-ins 44)) 2.5 0 "1")

(command "_TEXT" "_MC" (list (+ x-pnt-ins 247.5) (- y-pnt-ins 4)) 2.5 0 "ООО НПФ \"ДИНФО\",");производитель
(command "_TEXT" "_MC" (list (+ x-pnt-ins 247.5) (- y-pnt-ins 12)) 2.5 0 "г. Москва")
(command "_TEXT" "_MC" (list (+ x-pnt-ins 247.5) (- y-pnt-ins 44)) 2.5 0 "ООО НПФ \"ДИНФО\",")
(command "_TEXT" "_MC" (list (+ x-pnt-ins 247.5) (- y-pnt-ins 52)) 2.5 0 "г. Москва")

(command "_TEXT" "_ML" (list (+ x-pnt-ins 336) (- y-pnt-ins 4)) 2.5 0 "Свидетельство");сертификат
(command "_TEXT" "_ML" (list (+ x-pnt-ins 336) (- y-pnt-ins 12)) 2.5 0 "RU.C.29.004.A №36476,")
(command "_TEXT" "_ML" (list (+ x-pnt-ins 336) (- y-pnt-ins 20)) 2.5 0 "№ 41550-09")
(command "_TEXT" "_ML" (list (+ x-pnt-ins 336) (- y-pnt-ins 28)) 2.5 0 "в Госреестре СИ")

(setvar "osmode" 6199)
(setvar "cmdecho" 1)
(vla-endundomark adoc)
(princ)
)
;/////// конец программы ///////
