;/////// ************************************************************ ////////////////////////////////////////////////////////////
;/////// рисование знака закладной конструкции на ссвп                ////////////////////////////////////////////////////////////
;/////// ************************************************************ ////////////////////////////////////////////////////////////
(defun c:05-embedded-construction

( / adoc line-1 pnt-ins)
   
(vl-load-com)
(vla-startundomark
  (setq adoc (vla-get-activedocument (vlax-get-acad-object)));setq
);start undo

;;;;;;; блок знак кабеля 15 мм
(if (= (tblsearch "block" "ссвп-закладная-конструкция") nil)
	(progn
		(setvar "osmode" 0)
		(setvar "celweight" 120)
		(command "_line" '(0 0) '(0 -4) "")
		(setq line-1 (entlast))
				
		(command "_block" "ссвп-закладная-конструкция" '(0 0) line-1 "")
		(setvar "celweight" -1)
	);progn
);if

(setvar "osmode" 6199)

(setq pnt-ins (getpoint "\nУкажите точку оси\n"));setq

(setvar "osmode" 0)

(command "_insert" "ссвп-закладная-конструкция" "_x" 1 "_y" 1 "_z" 1 "_r" 0 pnt-ins)

(vla-endundomark adoc)

(setvar "osmode" 6199)
(setvar "cmdecho" 1)
(gc)
(princ)
)

;/////// *************************************************************////////////////////////////////////////////////////////////
;/////// КОНЕЦ ПРОГРАММЫ                                              ////////////////////////////////////////////////////////////
;/////// *************************************************************////////////////////////////////////////////////////////////
