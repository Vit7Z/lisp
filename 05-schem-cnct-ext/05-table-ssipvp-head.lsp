;/////// ************************************************************ ///////////////////////////////////////////////////////////////////////////////////////////////////////////
;///////                                                              ///////////////////////////////////////////////////////////////////////////////////////////////////////////
(defun c:05-table-ssipvp-head

( / adoc pnt-1 rctn-1 rctn-10 rctn-11 rctn-12 rctn-13 rctn-14 rctn-15 rctn-2 rctn-3 rctn-4 rctn-5 rctn-6 rctn-7 rctn-8 rctn-9 txt-1 txt-10 txt-11 txt-12 txt-13 txt-14 txt-15 txt-2 txt-3 txt-4 txt-5 txt-6 txt-7 txt-8 txt-9)

(setvar "cmdecho" 0)

(vl-load-com)
(vla-startundomark
  (setq adoc (vla-get-activedocument (vlax-get-acad-object))
  );setq
);start undo

(if (= (tblsearch "block" "ссвп-таблица-ссипвп-шапка" ) nil)
	(progn				; если данного блока нет
		(setvar	"OSMODE" 0)
		(setvar	"CLAYER" "0")
		(setvar "CELWEIGHT" 60)
		
 		(command "_RECTANGLE" '(-395 0) '(-370 -40))
		(setq rctn-1 (entlast))
 		(command "_RECTANGLE" '(-370 0) '(-280 -8))
		(setq rctn-2 (entlast))	
		(command "_RECTANGLE" '(-370 -8) '(-325 -40))	
		(setq rctn-3 (entlast))
		(command "_RECTANGLE" '(-325 -8) '(-280 -40))
		(setq rctn-4 (entlast))
		(command "_RECTANGLE" '(-280 0) '(-220 -40))
		(setq rctn-5 (entlast))
		(command "_RECTANGLE" '(-220 0) '(-130 -8))
		(setq rctn-6 (entlast))
		(command "_RECTANGLE" '(-220 -8) '(-170 -40))
		(setq rctn-7 (entlast))
    (command "_RECTANGLE" '(-170 -8) '(-130 -16))
		(setq rctn-8 (entlast))
		(command "_RECTANGLE" '(-170 -16) '(-150 -40))
		(setq rctn-9 (entlast))
		(command "_RECTANGLE" '(-150 -16) '(-130 -40))
		(setq rctn-10 (entlast))
		(command "_RECTANGLE" '(-130 0) '(-60 -8))
		(setq rctn-11 (entlast))
		(command "_RECTANGLE" '(-130 -8) '(-80 -40))
		(setq rctn-12 (entlast))
		(command "_RECTANGLE" '(-80 -8) '(-60 -40))
		(setq rctn-13 (entlast))
		(command "_RECTANGLE" '(-60 0) '(-40 -40))
		(setq rctn-14 (entlast))
		(command "_RECTANGLE" '(-40 0) '(0 -40))
		(setq rctn-15 (entlast))
		
		(setvar "CELWEIGHT" -1)

		(setq txt-1
			(entmakex
				(list
					'(0 . "MTEXT")
					'(100 . "AcDbEntity")
					'(100 . "AcDbMText")
					'(10 -382.5 -20) ; нач точка текста
					'(1 . "Кабель, жгут, труба}") ; содержание текста
					'(40 . 3.5) ; высота текста
					'(41 . 24) ; растяжение текста
					'(42 . 24) ; ширина текста
					'(71 . 5) ; гориз выравнивание текста
					'(370 . -1) ; толщина текста
					 (cons 7 (getvar "textstyle")) ; стиль текста
				) ; end of list
			); entmakex
		); setq

		(setq txt-2
			(entmakex
				(list
					'(0 . "TEXT")
					'(100 . "AcDbEntity")
					'(100 . "AcDbText")
					'(10 -325 -4) ; нач точка текста
					'(11 -325 -4) ; нач точка текста
					'(1 . "Направление") ; содержание текста
					'(40 . 3.5) ; высота текста
					'(41 . 1) ; растяжение текста
					'(50 . 0) ; поворот текста
					'(72 . 1) ; гориз выравнивание текста
					'(73 . 2) ; верт выравнивание текста
					'(370 . -1) ; толщина текста
					 (cons 7 (getvar "textstyle")) ; стиль текста
				) ; end of list
			); entmakex
		); setq
				
		(setq txt-3 
			(entmakex
				(list
					'(0 . "TEXT")
					'(100 . "AcDbEntity")
					'(100 . "AcDbText")
					'(10 -347.5 -24) ; нач точка текста
					'(11 -347.5 -24) ; нач точка текста
					'(1 . "откуда") ; содержание текста
					'(40 . 3.5) ; высота текста
					'(41 . 1) ; растяжение текста
					'(50 . 0) ; поворот текста
					'(72 . 1) ; гориз выравнивание текста
					'(73 . 2) ; верт выравнивание текста
					'(370 . -1) ; толщина текста
					 (cons 7 (getvar "textstyle")) ; стиль текста
				) ; end of list
			); entmakex
		); setq				

		(setq txt-4
			(entmakex
				(list
					'(0 . "TEXT")
					'(100 . "AcDbEntity")
					'(100 . "AcDbText")
					'(10 -302.5 -24) ; нач точка текста
					'(11 -302.5 -24) ; нач точка текста
					'(1 . "куда") ; содержание текста
					'(40 . 3.5) ; высота текста
					'(41 . 1) ; растяжение текста
					'(50 . 0) ; поворот текста
					'(72 . 1) ; гориз выравнивание текста
					'(73 . 2) ; верт выравнивание текста
					'(370 . -1) ; толщина текста
					 (cons 7 (getvar "textstyle")) ; стиль текста
				) ; end of list
			); entmakex
		); setq

		(setq txt-5
			(entmakex
				(list
					'(0 . "MTEXT")
					'(100 . "AcDbEntity")
					'(100 . "AcDbMText")
					'(10 -250 -20) ; нач точка текста
					'(1 . "Направление по чертежам расположения}") ; содержание текста
					'(40 . 3.5) ; высота текста
					'(41 . 20) ; растяжение текста
					'(42 . 20) ; ширина текста
					'(71 . 5) ; гориз выравнивание текста
					'(370 . -1) ; толщина текста
					 (cons 7 (getvar "textstyle")) ; стиль текста
				) ; end of list
			); entmakex
		); setq
		
		(setq txt-6
			(entmakex
				(list
					'(0 . "TEXT")
					'(100 . "AcDbEntity")
					'(100 . "AcDbText")
					'(10 -175 -4) ; нач точка текста
					'(11 -175 -4) ; нач точка текста
					'(1 . "Кабель, провод") ; содержание текста
					'(40 . 3.5) ; высота текста
					'(41 . 1) ; растяжение текста
					'(50 . 0) ; поворот текста
					'(72 . 1) ; гориз выравнивание текста
					'(73 . 2) ; верт выравнивание текста
					'(370 . -1) ; толщина текста
					 (cons 7 (getvar "textstyle")) ; стиль текста
				) ; end of list
			); entmakex
		); setq
		
		(setq txt-7
			(entmakex
				(list
					'(0 . "MTEXT")
					'(100 . "AcDbEntity")
					'(100 . "AcDbMText")
					'(10 -195 -24) ; нач точка текста
					'(1 . "Марка, число жил сечение}") ; содержание текста
					'(40 . 3.5) ; высота текста
					'(41 . 33) ; растяжение текста
					'(42 . 33) ; ширина текста
					'(71 . 5) ; гориз выравнивание текста
					'(370 . -1) ; толщина текста
					 (cons 7 (getvar "textstyle")) ; стиль текста
				) ; end of list
			); entmakex
		); setq

		(setq txt-8
			(entmakex
				(list
					'(0 . "TEXT")
					'(100 . "AcDbEntity")
					'(100 . "AcDbText")
					'(10 -150 -12) ; нач точка текста
					'(11 -150 -12) ; нач точка текста
					'(1 . "Длина, м.") ; содержание текста
					'(40 . 3.5) ; высота текста
					'(41 . 1) ; растяжение текста
					'(50 . 0) ; поворот текста
					'(72 . 1) ; гориз выравнивание текста
					'(73 . 2) ; верт выравнивание текста
					'(370 . -1) ; толщина текста
					 (cons 7 (getvar "textstyle")) ; стиль текста
				) ; end of list
			); entmakex
		); setq	
		
		(setq txt-9
			(entmakex
				(list
					'(0 . "MTEXT")
					'(100 . "AcDbEntity")
					'(100 . "AcDbMText")
					'(10 -160 -28) ; нач точка текста
					'(1 . "проек-\\Pтируе-\\Pмая") ; содержание текста
					'(40 . 3.5) ; высота текста
					'(41 . 20) ; растяжение текста
					'(42 . 20) ; ширина текста
					'(71 . 5) ; гориз выравнивание текста
					'(370 . -1) ; толщина текста
					 (cons 7 (getvar "textstyle")) ; стиль текста
				) ; end of list
			); entmakex
		); setq

		(setq txt-10
			(entmakex
				(list
					'(0 . "MTEXT")
					'(100 . "AcDbEntity")
					'(100 . "AcDbMText")
					'(10 -140 -28) ; нач точка текста
					'(1 . "факти-\\Pчес-\\Pкая}") ; содержание текста
					'(40 . 3.5) ; высота текста
					'(41 . 20) ; растяжение текста
					'(42 . 20) ; ширина текста
					'(71 . 5) ; гориз выравнивание текста
					'(370 . -1) ; толщина текста
					 (cons 7 (getvar "textstyle")) ; стиль текста
				) ; end of list
			); entmakex
		); setq

		(setq txt-11
			(entmakex
				(list
					'(0 . "TEXT")
					'(100 . "AcDbEntity")
					'(100 . "AcDbText")
					'(10 -95 -4) ; нач точка текста
					'(11 -95 -4) ; нач точка текста
					'(1 . "Труба") ; содержание текста
					'(40 . 3.5) ; высота текста
					'(41 . 1) ; растяжение текста
					'(50 . 0) ; поворот текста
					'(72 . 1) ; гориз выравнивание текста
					'(73 . 2) ; верт выравнивание текста
					'(370 . -1) ; толщина текста
					 (cons 7 (getvar "textstyle")) ; стиль текста
				) ; end of list
			); entmakex
		); setq	

		(setq txt-12
			(entmakex
				(list
					'(0 . "MTEXT")
					'(100 . "AcDbEntity")
					'(100 . "AcDbMText")
					'(10 -105 -24) ; нач точка текста
					'(1 . "Марка, диаметр}") ; содержание текста
					'(40 . 3.5) ; высота текста
					'(41 . 20) ; растяжение текста
					'(42 . 20) ; ширина текста
					'(71 . 5) ; гориз выравнивание текста
					'(370 . -1) ; толщина текста
					 (cons 7 (getvar "textstyle")) ; стиль текста
				) ; end of list
			); entmakex
		); setq

		(setq txt-13
			(entmakex
				(list
					'(0 . "MTEXT")
					'(100 . "AcDbEntity")
					'(100 . "AcDbMText")
					'(10 -70 -24) ; нач точка текста
					'(1 . "Длина, м.") ; содержание текста
					'(40 . 3.5) ; высота текста
					'(41 . 20) ; растяжение текста
					'(42 . 20) ; ширина текста
					'(71 . 5) ; гориз выравнивание текста
					'(370 . -1) ; толщина текста
					 (cons 7 (getvar "textstyle")) ; стиль текста
				) ; end of list
			); entmakex
		); setq

		(setq txt-14
			(entmakex
				(list
					'(0 . "MTEXT")
					'(100 . "AcDbEntity")
					'(100 . "AcDbMText")
					'(10 -50 -20) ; нач точка текста
					'(1 . "Измери-\\Pтель-\\Pная цепь") ; содержание текста
					'(40 . 3.5) ; высота текста
					'(41 . 20) ; растяжение текста
					'(42 . 20) ; ширина текста
					'(71 . 5) ; гориз выравнивание текста
					'(370 . -1) ; толщина текста
					 (cons 7 (getvar "textstyle")) ; стиль текста
				) ; end of list
			); entmakex
		); setq
		
		(setq txt-15
			(entmakex
				(list
					'(0 . "MTEXT")
					'(100 . "AcDbEntity")
					'(100 . "AcDbMText")
					'(10 -20 -20) ; нач точка текста
					'(1 . "Чертеж установки}") ; содержание текста
					'(40 . 3.5) ; высота текста
					'(41 . 20) ; растяжение текста
					'(42 . 20) ; ширина текста
					'(71 . 5) ; гориз выравнивание текста
					'(370 . -1) ; толщина текста
					 (cons 7 (getvar "textstyle")) ; стиль текста
				) ; end of list
			); entmakex
		); setq		
		
		
		(command "_block" "ссвп-таблица-ссипвп-шапка" '(0 0) 
  		rctn-1 rctn-2 rctn-3 rctn-4 rctn-5 rctn-6 rctn-7 rctn-8 rctn-9 rctn-10 rctn-11 rctn-12 rctn-13 rctn-14 rctn-15 
  		txt-1 txt-2 txt-3 txt-4 txt-5 txt-6 txt-7 txt-8 txt-9 txt-10 txt-11 txt-12 txt-13 txt-14 txt-15
  	"")
  ); end progn
); end if

(setvar	"osmode" 6199)

(setq pnt-1 (getpoint "\nУкажите точку вставки\n")
);setq

(command "_insert" "ссвп-таблица-ссипвп-шапка" "_X" 1 "_Y" 1 "_Z" 1 "_R" 0 pnt-1) ; если блок существует





(vla-endundomark adoc)	
(setvar "osmode" 6199)
(setvar "cmdecho" 1)
(princ)
)
;///////                                                              ///////////////////////////////////////////////////////////////////////////////////////////////////////////
;/////// ************************************************************ ///////////////////////////////////////////////////////////////////////////////////////////////////////////
