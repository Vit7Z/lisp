;/////// ************************************************************ ///////////////////////////////////////////////////////////////////////////////////////////////////////////
;/////// рисование линийс разными урвнями начала на один уровень      ///////////////////////////////////////////////////////////////////////////////////////////////////////////
;/////// ************************************************************ ///////////////////////////////////////////////////////////////////////////////////////////////////////////
(defun c:05-pnt-to-lvl

( / adoc pnt-1 pnt-ins xpnt-ins ypnt-1)

(vl-load-com)

(vla-startundomark
  (setq adoc (vla-get-activedocument (vlax-get-acad-object)));setq
);start undo

(setvar "cmdecho" 0)

(setq pnt-1 (getpoint "\nУкажите точку уровня\n")
			ypnt-1 (nth 1 pnt-1)
);setq

(while (/= (setq pnt-ins (getpoint "\nУкажите точку\n")) nil)
  (progn
    (setq xpnt-ins (nth 0 pnt-ins)
    			pnt-1 (list xpnt-ins ypnt-1)
    );setq
    (setvar "osmode" 0)
		(command "_line" pnt-ins pnt-1 "")
		(setvar "osmode" 6199)
  );progn
);while



(setvar "osmode" 6199)
(setvar "cmdecho" 1)
(vla-endundomark adoc)
(princ)
)
;/////// конец программы ////////////////////////////////////////////////////////////////////////////////////////////////////////////////////////////////////////////////////////
