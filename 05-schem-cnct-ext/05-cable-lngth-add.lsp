;/////// ************************************************************ ///////////////////////////////////////////////////////////////////////////////////////////////////////////
;///////                                                              ///////////////////////////////////////////////////////////////////////////////////////////////////////////
;/////// ************************************************************ ///////////////////////////////////////////////////////////////////////////////////////////////////////////
(defun c:05-cable-lngth-add

( / adoc crnt-obj data data-txt dlt-01 txt-tmp)

(vl-load-com)

(vla-startundomark (setq adoc (vla-get-activedocument (vlax-get-acad-object))));start undo

(setvar "cmdecho" 0)

(setq dlt-01 (getint "\nВведите приращение\n"));setq

(while (/= (setq crnt-obj (car (entsel "\nВыберите длину кабеля\n"))) nil)

	(setq	data (entget crnt-obj)
	
				data-txt (assoc 1 data)
				
				txt-tmp (cdr data-txt)
			
				txt-tmp (substr txt-tmp 1 (vl-string-search "м" txt-tmp))
						
				txt-tmp (+ (atoi txt-tmp) dlt-01)
				
				txt-tmp (strcat (itoa txt-tmp) " м")
				
				txt-tmp (cons 1 txt-tmp)
				
				data (subst	txt-tmp data-txt data)
	);setq
	
	(entmod data)

);while



(setvar "osmode" 6199)
(setvar "cmdecho" 1)
(vla-endundomark adoc)
(princ)
)
;;;;/////////////////////////////////////////////////////////////////////////////////////////////////////////////////////////////////////////////////////////////////////////////
;/////// конец программы ////////////////////////////////////////////////////////////////////////////////////////////////////////////////////////////////////////////////////////
;;;;/////////////////////////////////////////////////////////////////////////////////////////////////////////////////////////////////////////////////////////////////////////////
