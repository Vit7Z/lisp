;////////////////////////////////////////////////////////////////////////////////////////////////////////////////////////////////////////////////////////////////////////////////
;/////// уго сосуд конденсационный //////////////////////////////////////////////////////////////////////////////////////////////////////////////////////////////////////////////
;////////////////////////////////////////////////////////////////////////////////////////////////////////////////////////////////////////////////////////////////////////////////
(defun c:05-vessel-condensat

( / circle-1 line-1 pnt-ins)
(setvar "CMDECHO" 0)
(command "_.undo" "_begin")

(setvar "osmode" 0)
(if (= (tblsearch "block" "сосуд-конденсационный-ссвп" ) nil)
	(progn
		(command "_.LINE" '(-3 0) '(3 0) "")
		(setq line-1 (entlast))
		(command "_circle" '(0 0) 3)
		(setq circle-1 (entlast))
		(command "_block" "сосуд-конденсационный-ссвп"	'(0 3) line-1 circle-1 "")
	);progn
);if

(setvar "osmode" 6199)
(setvar "ORTHOMODE" 0)

(while (/= (setq pnt-ins (getpoint )) nil)
  (progn
    (command "_insert" "сосуд-конденсационный-ссвп" "_x" 1 "_y" 1 "_z" 1 "_r" 0 pnt-ins)   
  );progn
);while

(command "_.undo" "_end")
(setvar "osmode" 6199)
(setvar "CMDECHO" 1)
(princ)
)
; //////// конец программы //////////
