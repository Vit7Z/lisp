;/////// ************************************************************ ///////////////////////////////////////////////////////////////////////////////////////////////////////////
;///////                                                              ///////////////////////////////////////////////////////////////////////////////////////////////////////////
;/////// ************************************************************ ///////////////////////////////////////////////////////////////////////////////////////////////////////////
(defun c:05-pipe-pulse-numbering

( / adoc crnt-txt sel-txt-old sel-txt-typ slct-txt start-num str-new)

(vl-load-com)
(vla-startundomark (setq adoc (vla-get-activedocument (vlax-get-acad-object))));start undo

(setvar "cmdecho" 0)

(setq start-num (atoi (getstring "\nВведите начальное значение\n")));setq

(if (= start-num 0)
	(setq slct-txt (entget (car (entsel "\nВыберите начальное обозначение\n")))
				start-num (atoi (cdr (assoc 1 slct-txt)))
				start-num (+ start-num 1)
	);setq
);if

(while (/= nil (setq crnt-txt (entget (car (entsel "\nВыберите обозначение\n")))))
	(setq str-new (strcat "0" (itoa start-num))
				str-new (cons 1 str-new)
				
				sel-txt-typ (cdr (assoc 0 crnt-txt))
				sel-txt-old (assoc 1 crnt-txt)
				
				crnt-txt (subst str-new sel-txt-old crnt-txt)	;заменяем старую строку новой
				start-num (1+ start-num)
	);setq
	
	(entmod crnt-txt)	;обновляем данные примитива
);while

(setvar "osmode" 6199)
(setvar "cmdecho" 1)
(vla-endundomark adoc)
(princ)
)
;;;;/////////////////////////////////////////////////////////////////////////////////////////////////////////////////////////////////////////////////////////////////////////////
;/////// конец программы ////////////////////////////////////////////////////////////////////////////////////////////////////////////////////////////////////////////////////////
;;;;/////////////////////////////////////////////////////////////////////////////////////////////////////////////////////////////////////////////////////////////////////////////
