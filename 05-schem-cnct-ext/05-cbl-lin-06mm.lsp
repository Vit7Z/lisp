;/////// ************************************************************ //////////////////////////////////////////////////////////////////
;/////// рисование объединяющей линии 0.6мм для ссвп                  //////////////////////////////////////////////////////////////////
;/////// ************************************************************ //////////////////////////////////////////////////////////////////
(defun c:05-cbl-lin-06mm 

( / pnt-l pnt-r)

(setvar "cmdecho" 0)

(setvar "osmode" 6199)
	
(while (/= (setq pnt-l (getpoint "\nУкажите левую точку\n")) nil)
	(progn
		(setq pnt-r (getpoint "\nУкажите правую точку\n"));setq)
		(setvar "osmode" 0)
		(setvar "celweight" 60)
		(command "_line" pnt-l pnt-r "")
		(setvar "celweight" -1)
		(setvar "osmode" 6199)
	);progn
);while

(setvar "cmdecho" 0)
(setvar "osmode" 6199)
(princ)
)
;;; //////////// конец программы ////////////////////////////////////////////////////////////////////////
